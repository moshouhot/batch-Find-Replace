;|*****************************************************************************
OA图框工具：DCL对话框响应主程序
--含标准图框和大项目图框
--全局系统变量如下：
    MEAAD_AZML_V31                 软件安装目录
    MEAAD_PDFPRN               PDF打印机名称
    MEAAD_PDFPRN_PATH          PDF打印机输出目录
    Meaad_all_Scale            全局比例因子 
|;
;;*****************************************************************************
(DEFUN c:kkk()
(OATK_DCL)
)

(DEFUN OATK_DCL(/ acadobj opobj filesobj supfile dcl_EAAD CZmode)

  ;-------------------设置软件MEAAD目录安装位置-------------------------------------------------
    (setq MEAAD_AZML_V31 "d:\\meaad3.0\\")
  ;------------------------------------------------------------------------------------------------------
    (vl-load-com)
    (setq acadobj (vlax-get-acad-object))
    (setq opobj (vla-get-preferences acadobj))
    (setq filesobj (vla-get-files opobj))
    (setq supfile (vla-get-SupportPath filesobj))
    (setvar "insunits" 0)
    (if (not (wcmatch supfile "*\\meaad3.0\\*"))   (setq supfile (strcat supfile ";" MEAAD_AZML_V31)))
    (if (not (wcmatch supfile "*\\二次参考图3.0\\*")) (setq supfile (strcat supfile ";" MEAAD_AZML_V31 "二次参考图3.0\\")))
    (if (not (wcmatch supfile "*\\OA图框3.0\\*"))     (setq supfile (strcat supfile ";" MEAAD_AZML_V31 "OA图框3.0\\")))
    (if (not (wcmatch supfile "*\\工程信息3.0\\*"))   (setq supfile (strcat supfile ";" MEAAD_AZML_V31 "工程信息3.0\\")))
    (vla-put-SupportPath filesobj supfile)
    (setq dcl_EAAD (load_dialog "Meaad_OATK_3.0.dcl"))
    (if (not  (new_dialog "MEAAD3_OA_TK1" dcl_EAAD))
    (exit))  
    (set_tile "OATKLX1" "1")
    (set_tile "OATKFX1" "1")
    (set_tile "OATKBL1" "1")
    (set_tile "JBTF_A2" "1")
    (set_tile "TFZF_00" "1")

    (setq CZmode "")

    (action_tile "DHK_OA_INSERT" "(DHK_TKXX) (setq CZmode $key) (setq Meaad_all_Scale TK_SCALE) (done_dialog 1)")
    (action_tile "DHK_OA_CHANGE" "(DHK_TKXX) (setq CZmode $key) (setq Meaad_all_Scale TK_SCALE) (done_dialog 1)")

    (action_tile "DHK_OA_TKSCZS" "(setq CZmode $key) (done_dialog 1)")
    (action_tile "DHK_OA_CKTJSX" "(setq CZmode $key) (done_dialog 1)")
    (action_tile "DHK_OA_GCTKZH" "(setq CZmode $key) (done_dialog 1)")
    (action_tile "DHK_OA_THBHZS" "(setq CZmode $key) (done_dialog 1)")
    (action_tile "DHK_OA_TKJZCP" "(setq CZmode $key) (done_dialog 1)")


    (action_tile "DHK_OA_THZJTZ" "(setq CZmode $key) (done_dialog 1)")
    (action_tile "DHK_OA_TKBJQ" "(setq CZmode $key) (done_dialog 1)")
    (action_tile "DHK_OA_TKWZGW" "(setq CZmode $key) (done_dialog 1)")
    (action_tile "DHK_OA_DYCKFJ" "(setq CZmode $key) (done_dialog 1)")
    (action_tile "DHK_OA_TMTHCD" "(setq CZmode $key) (done_dialog 1)")


    (action_tile "DHK_OA_GCXXZS" "(setq CZmode $key) (done_dialog 1)")
    (action_tile "DHK_OA_CSMLSC" "(setq CZmode $key) (done_dialog 1)")
    (action_tile "DHK_OA_MLQJSX" "(setq CZmode $key) (done_dialog 1)")
    (action_tile "DHK_OA_MLJBTZ" "(setq CZmode $key) (done_dialog 1)")
    (action_tile "DHK_OA_MLBJQ" "(setq CZmode $key) (done_dialog 1)")

    (action_tile "DHK_OA_JRCTFZ" "(setq CZmode $key) (done_dialog 1)")
    (action_tile "DHK_NOOA_CRQM" "(setq CZmode $key) (done_dialog 1)")
    (action_tile "DHK_OA_OAPDFPLDY" "(setq CZmode $key) (done_dialog 1)")
    (action_tile "DHK_OA_TZSLTJ" "(setq CZmode $key) (done_dialog 1)")
    (action_tile "cancel" "(setq CZmode $key) (done_dialog 0)")

    (start_dialog)
    (unload_dialog dcl_EAAD)

    (cond ((= czmode "DHK_OA_INSERT") (DHK_TKCR))
          ((= czmode "DHK_OA_CHANGE") (DHK_TKTH))

          ((= czmode "DHK_OA_TKSCZS") (DHK_OATKSCZS))
          ((= czmode "DHK_OA_CKTJSX") (DHK_OACKTJSX))
          ((= czmode "DHK_OA_GCTKZH") (DHK_OAGCTKZH))
          ((= czmode "DHK_OA_THBHZS") (DHK_OATHBHZS))
          ((= czmode "DHK_OA_TKJZCP") (DHK_OATKJZCP))

          ((= czmode "DHK_OA_THZJTZ") (DHK_OATHZJTZ))
          ((= czmode "DHK_OA_TKBJQ") (DHK_OATKBJQ))
          ((= czmode "DHK_OA_TKWZGW") (DHK_OATKWZGW))
          ((= czmode "DHK_OA_DYCKFJ") (DHK_OADYCKFJ))
          ((= czmode "DHK_OA_TMTHCD") (DHK_OATMTHCD))

          ((= czmode "DHK_OA_GCXXZS") (DHK_OAGCXXZS))
          ((= czmode "DHK_OA_CSMLSC") (DHK_OACSMLSC))
          ((= czmode "DHK_OA_MLQJSX") (DHK_OAMLQJSX))
          ((= czmode "DHK_OA_MLJBTZ") (DHK_OAMLJBTZ))
          ((= czmode "DHK_OA_MLBJQ") (DHK_OAMLBJQ))

          ((= czmode "DHK_OA_JRCTFZ") (DHK_OAJRCTFZ))
          ((= czmode "DHK_NOOA_CRQM") (DHK_NOOACRQM))
          ((= czmode "DHK_OA_OAPDFPLDY") (DHK_OAPDFPLDY))
          ((= czmode "DHK_OA_TZSLTJ") (DHK_OATZSLTJ))
    )
)


;|*****************************************************************************
OA图框工具：图框插入设定参数的读入 
|;
;;*****************************************************************************
(defun DHK_TKXX(/ TK_code1 TK_code2 TK_code3 TK_code4)
                (if (= "1" (get_tile "OATKLX1")) (setq TK_code1 "1"))
                (if (= "1" (get_tile "OATKLX2")) (setq TK_code1 "2"))
                (if (= "1" (get_tile "OATKFX1")) (setq TK_code2 "1"))
                (if (= "1" (get_tile "OATKFX2")) (setq TK_code2 "2"))
                (if (= "1" (get_tile "OATKBL1")) (setq TK_SCALE 1))
                (if (= "1" (get_tile "OATKBL2")) (setq TK_SCALE 100))
                (if (= "1" (get_tile "OATKBL3")) (setq TK_SCALE 200))
                (if (= "1" (get_tile "OATKBL4")) (setq TK_SCALE 1000))
                (if (= "1" (get_tile "JBTF_A3")) (setq TK_code3 "1"))
                (if (= "1" (get_tile "JBTF_A2")) (setq TK_code3 "2"))
                (if (= "1" (get_tile "JBTF_A1")) (setq TK_code3 "3"))
                (if (= "1" (get_tile "JBTF_A0")) (setq TK_code3 "4"))
                (if (= "1" (get_tile "JBTF_KK")) (setq TK_code3 "5"))
                (if (= "1" (get_tile "JBTF_ML")) (setq TK_code3 "6"))
                (if (= "1" (get_tile "JBTF_CZ")) (setq TK_code3 "7"))
                (if (= "1" (get_tile "TFZF_00")) (setq TK_code4 "1"))
                (if (= "1" (get_tile "TFZF_18")) (setq TK_code4 "2"))
                (if (= "1" (get_tile "TFZF_14")) (setq TK_code4 "3"))
                (if (= "1" (get_tile "TFZF_12")) (setq TK_code4 "4"))
                (if (= "1" (get_tile "TFZF_34")) (setq TK_code4 "5"))
                (if (= "1" (get_tile "TFZF_44")) (setq TK_code4 "6"))
                (setq TK_code (strcat TK_code1 TK_code2 TK_code3 TK_code4))     
)




;|*****************************************************************************
OA图框工具：插入图框子功能模块
--遗留问题：标准图框和大项目图框的明确区分
|;
;;*****************************************************************************
(defun DHK_TKCR()
        (cond ((= TK_code "1111") (command "insert" "OA图框_A3_420_横框_标准" pause TK_scale TK_scale 0 "" "" "explode" "L"))
              ((= TK_code "1112") (command "insert" "OA图框_A3加_472_横框_标准" pause TK_scale TK_scale 0 "" "" "explode" "L"))
              ((= TK_code "1113") (command "insert" "OA图框_A3加_525_横框_标准" pause TK_scale TK_scale 0 "" "" "explode" "L"))
              ((= TK_code "1114") (command "insert" "OA图框_A3加_630_横框_标准" pause TK_scale TK_scale 0 "" "" "explode" "L"))
              ((= TK_code "1115") (command "insert" "OA图框_A3加_735_横框_标准" pause TK_scale TK_scale 0 "" "" "explode" "L"))
              ((= TK_code "1116") (command "insert" "OA图框_A3加_840_横框_标准" pause TK_scale TK_scale 0 "" "" "explode" "L"))
              ((= TK_code "1121") (command "insert" "OA图框_A2_594_横框_标准" pause TK_scale TK_scale 0 "" "" "explode" "L"))
              ((= TK_code "1122") (command "insert" "OA图框_A2加_668_横框_标准" pause TK_scale TK_scale 0 "" "" "explode" "L"))
              ((= TK_code "1123") (command "insert" "OA图框_A2加_742_横框_标准" pause TK_scale TK_scale 0 "" "" "explode" "L"))
              ((= TK_code "1124") (command "insert" "OA图框_A2加_891_横框_标准" pause TK_scale TK_scale 0 "" "" "explode" "L"))
              ((= TK_code "1125") (command "insert" "OA图框_A2加_1039_横框_标准" pause TK_scale TK_scale 0 "" "" "explode" "L"))
              ((= TK_code "1126") (command "insert" "OA图框_A2加_1188_横框_标准" pause TK_scale TK_scale 0 "" "" "explode" "L"))
              ((= TK_code "1131") (command "insert" "OA图框_A1_841_横框_标准" pause TK_scale TK_scale 0 "" "" "explode" "L"))
              ((= TK_code "1132") (command "insert" "OA图框_A1加_946_横框_标准" pause TK_scale TK_scale 0 "" "" "explode" "L"))
              ((= TK_code "1133") (command "insert" "OA图框_A1加_1051_横框_标准" pause TK_scale TK_scale 0 "" "" "explode" "L"))
              ((= TK_code "1134") (command "insert" "OA图框_A1加_1261_横框_标准" pause TK_scale TK_scale 0 "" "" "explode" "L"))
              ((= TK_code "1135") (command "insert" "OA图框_A1加_1471_横框_标准" pause TK_scale TK_scale 0 "" "" "explode" "L"))
              ((= TK_code "1136") (command "insert" "OA图框_A1加_1682_横框_标准" pause TK_scale TK_scale 0 "" "" "explode" "L"))
              ((= TK_code "1141") (command "insert" "OA图框_A0_1189_横框_标准" pause TK_scale TK_scale 0 "" "" "explode" "L"))
              ((= TK_code "1142") (command "insert" "OA图框_A0加_1337_横框_标准" pause TK_scale TK_scale 0 "" "" "explode" "L"))
              ((= TK_code "1143") (command "insert" "OA图框_A0加_1486_横框_标准" pause TK_scale TK_scale 0 "" "" "explode" "L"))
              ((= TK_code "1144") (command "insert" "OA图框_A0加_1783_横框_标准" pause TK_scale TK_scale 0 "" "" "explode" "L"))
              ((= TK_code "1145") (command "insert" "OA图框_A0加_2080_横框_标准" pause TK_scale TK_scale 0 "" "" "explode" "L"))
              ((= TK_code "1146") (command "insert" "OA图框_A0加_2378_横框_标准" pause TK_scale TK_scale 0 "" "" "explode" "L"))

              ((= TK_code "2111") (command "insert" "OA图框_A3_420_横框_大项目" pause TK_scale TK_scale 0 "" "" "explode" "L"))
              ((= TK_code "2112") (command "insert" "OA图框_A3加_472_横框_大项目" pause TK_scale TK_scale 0 "" "" "explode" "L"))
              ((= TK_code "2113") (command "insert" "OA图框_A3加_525_横框_大项目" pause TK_scale TK_scale 0 "" "" "explode" "L"))
              ((= TK_code "2114") (command "insert" "OA图框_A3加_630_横框_大项目" pause TK_scale TK_scale 0 "" "" "explode" "L"))
              ((= TK_code "2115") (command "insert" "OA图框_A3加_735_横框_大项目" pause TK_scale TK_scale 0 "" "" "explode" "L"))
              ((= TK_code "2116") (command "insert" "OA图框_A3加_840_横框_大项目" pause TK_scale TK_scale 0 "" "" "explode" "L"))
              ((= TK_code "2121") (command "insert" "OA图框_A2_594_横框_大项目" pause TK_scale TK_scale 0 "" "" "explode" "L"))
              ((= TK_code "2122") (command "insert" "OA图框_A2加_668_横框_大项目" pause TK_scale TK_scale 0 "" "" "explode" "L"))
              ((= TK_code "2123") (command "insert" "OA图框_A2加_742_横框_大项目" pause TK_scale TK_scale 0 "" "" "explode" "L"))
              ((= TK_code "2124") (command "insert" "OA图框_A2加_891_横框_大项目" pause TK_scale TK_scale 0 "" "" "explode" "L"))
              ((= TK_code "2125") (command "insert" "OA图框_A2加_1039_横框_大项目" pause TK_scale TK_scale 0 "" "" "explode" "L"))
              ((= TK_code "2126") (command "insert" "OA图框_A2加_1188_横框_大项目" pause TK_scale TK_scale 0 "" "" "explode" "L"))
              ((= TK_code "2131") (command "insert" "OA图框_A1_841_横框_大项目" pause TK_scale TK_scale 0 "" "" "explode" "L"))
              ((= TK_code "2132") (command "insert" "OA图框_A1加_946_横框_大项目" pause TK_scale TK_scale 0 "" "" "explode" "L"))
              ((= TK_code "2133") (command "insert" "OA图框_A1加_1051_横框_大项目" pause TK_scale TK_scale 0 "" "" "explode" "L"))
              ((= TK_code "2134") (command "insert" "OA图框_A1加_1261_横框_大项目" pause TK_scale TK_scale 0 "" "" "explode" "L"))
              ((= TK_code "2135") (command "insert" "OA图框_A1加_1471_横框_大项目" pause TK_scale TK_scale 0 "" "" "explode" "L"))
              ((= TK_code "2136") (command "insert" "OA图框_A1加_1682_横框_大项目" pause TK_scale TK_scale 0 "" "" "explode" "L"))
              ((= TK_code "2141") (command "insert" "OA图框_A0_1189_横框_大项目" pause TK_scale TK_scale 0 "" "" "explode" "L"))
              ((= TK_code "2142") (command "insert" "OA图框_A0加_1337_横框_大项目" pause TK_scale TK_scale 0 "" "" "explode" "L"))
              ((= TK_code "2143") (command "insert" "OA图框_A0加_1486_横框_大项目" pause TK_scale TK_scale 0 "" "" "explode" "L"))
              ((= TK_code "2144") (command "insert" "OA图框_A0加_1783_横框_大项目" pause TK_scale TK_scale 0 "" "" "explode" "L"))
              ((= TK_code "2145") (command "insert" "OA图框_A0加_2080_横框_大项目" pause TK_scale TK_scale 0 "" "" "explode" "L"))
              ((= TK_code "2146") (command "insert" "OA图框_A0加_2378_横框_大项目" pause TK_scale TK_scale 0 "" "" "explode" "L"))

              ((= TK_code "1211") (command "insert" "OA图框_A3_420_竖框_标准" pause TK_scale TK_scale 0 "" "" "explode" "L"))
              ((= TK_code "1212") (command "insert" "OA图框_A3加_472_竖框_标准" pause TK_scale TK_scale 0 "" "" "explode" "L"))
              ((= TK_code "1213") (command "insert" "OA图框_A3加_525_竖框_标准" pause TK_scale TK_scale 0 "" "" "explode" "L"))
              ((= TK_code "1214") (command "insert" "OA图框_A3加_630_竖框_标准" pause TK_scale TK_scale 0 "" "" "explode" "L"))
              ((= TK_code "1215") (command "insert" "OA图框_A3加_735_竖框_标准" pause TK_scale TK_scale 0 "" "" "explode" "L"))
              ((= TK_code "1216") (command "insert" "OA图框_A3加_840_竖框_标准" pause TK_scale TK_scale 0 "" "" "explode" "L"))
              ((= TK_code "1221") (command "insert" "OA图框_A2_594_竖框_标准" pause TK_scale TK_scale 0 "" "" "explode" "L"))
              ((= TK_code "1222") (command "insert" "OA图框_A2加_668_竖框_标准" pause TK_scale TK_scale 0 "" "" "explode" "L"))
              ((= TK_code "1223") (command "insert" "OA图框_A2加_742_竖框_标准" pause TK_scale TK_scale 0 "" "" "explode" "L"))
              ((= TK_code "1224") (command "insert" "OA图框_A2加_891_竖框_标准" pause TK_scale TK_scale 0 "" "" "explode" "L"))
              ((= TK_code "1225") (command "insert" "OA图框_A2加_1039_竖框_标准" pause TK_scale TK_scale 0 "" "" "explode" "L"))
              ((= TK_code "1226") (command "insert" "OA图框_A2加_1188_竖框_标准" pause TK_scale TK_scale 0 "" "" "explode" "L"))
              ((= TK_code "1231") (command "insert" "OA图框_A1_841_竖框_标准" pause TK_scale TK_scale 0 "" "" "explode" "L"))
              ((= TK_code "1232") (command "insert" "OA图框_A1加_946_竖框_标准" pause TK_scale TK_scale 0 "" "" "explode" "L"))
              ((= TK_code "1233") (command "insert" "OA图框_A1加_1051_竖框_标准" pause TK_scale TK_scale 0 "" "" "explode" "L"))
              ((= TK_code "1234") (command "insert" "OA图框_A1加_1261_竖框_标准" pause TK_scale TK_scale 0 "" "" "explode" "L"))
              ((= TK_code "1235") (command "insert" "OA图框_A1加_1471_竖框_标准" pause TK_scale TK_scale 0 "" "" "explode" "L"))
              ((= TK_code "1236") (command "insert" "OA图框_A1加_1682_竖框_标准" pause TK_scale TK_scale 0 "" "" "explode" "L"))
              ((= TK_code "1241") (command "insert" "OA图框_A0_1189_竖框_标准" pause TK_scale TK_scale 0 "" "" "explode" "L"))
              ((= TK_code "1242") (command "insert" "OA图框_A0加_1337_竖框_标准" pause TK_scale TK_scale 0 "" "" "explode" "L"))
              ((= TK_code "1243") (command "insert" "OA图框_A0加_1486_竖框_标准" pause TK_scale TK_scale 0 "" "" "explode" "L"))
              ((= TK_code "1244") (command "insert" "OA图框_A0加_1783_竖框_标准" pause TK_scale TK_scale 0 "" "" "explode" "L"))
              ((= TK_code "1245") (command "insert" "OA图框_A0加_2080_竖框_标准" pause TK_scale TK_scale 0 "" "" "explode" "L"))
              ((= TK_code "1246") (command "insert" "OA图框_A0加_2378_竖框_标准" pause TK_scale TK_scale 0 "" "" "explode" "L"))

              ((= TK_code "2211") (command "insert" "OA图框_A3_420_竖框_大项目" pause TK_scale TK_scale 0 "" "" "explode" "L"))
              ((= TK_code "2212") (command "insert" "OA图框_A3加_472_竖框_大项目" pause TK_scale TK_scale 0 "" "" "explode" "L"))
              ((= TK_code "2213") (command "insert" "OA图框_A3加_525_竖框_大项目" pause TK_scale TK_scale 0 "" "" "explode" "L"))
              ((= TK_code "2214") (command "insert" "OA图框_A3加_630_竖框_大项目" pause TK_scale TK_scale 0 "" "" "explode" "L"))
              ((= TK_code "2215") (command "insert" "OA图框_A3加_735_竖框_大项目" pause TK_scale TK_scale 0 "" "" "explode" "L"))
              ((= TK_code "2216") (command "insert" "OA图框_A3加_840_竖框_大项目" pause TK_scale TK_scale 0 "" "" "explode" "L"))
              ((= TK_code "2221") (command "insert" "OA图框_A2_594_竖框_大项目" pause TK_scale TK_scale 0 "" "" "explode" "L"))
              ((= TK_code "2222") (command "insert" "OA图框_A2加_668_竖框_大项目" pause TK_scale TK_scale 0 "" "" "explode" "L"))
              ((= TK_code "2223") (command "insert" "OA图框_A2加_742_竖框_大项目" pause TK_scale TK_scale 0 "" "" "explode" "L"))
              ((= TK_code "2224") (command "insert" "OA图框_A2加_891_竖框_大项目" pause TK_scale TK_scale 0 "" "" "explode" "L"))
              ((= TK_code "2225") (command "insert" "OA图框_A2加_1039_竖框_大项目" pause TK_scale TK_scale 0 "" "" "explode" "L"))
              ((= TK_code "2226") (command "insert" "OA图框_A2加_1188_竖框_大项目" pause TK_scale TK_scale 0 "" "" "explode" "L"))
              ((= TK_code "2231") (command "insert" "OA图框_A1_841_竖框_大项目" pause TK_scale TK_scale 0 "" "" "explode" "L"))
              ((= TK_code "2232") (command "insert" "OA图框_A1加_946_竖框_大项目" pause TK_scale TK_scale 0 "" "" "explode" "L"))
              ((= TK_code "2233") (command "insert" "OA图框_A1加_1051_竖框_大项目" pause TK_scale TK_scale 0 "" "" "explode" "L"))
              ((= TK_code "2234") (command "insert" "OA图框_A1加_1261_竖框_大项目" pause TK_scale TK_scale 0 "" "" "explode" "L"))
              ((= TK_code "2235") (command "insert" "OA图框_A1加_1471_竖框_大项目" pause TK_scale TK_scale 0 "" "" "explode" "L"))
              ((= TK_code "2236") (command "insert" "OA图框_A1加_1682_竖框_大项目" pause TK_scale TK_scale 0 "" "" "explode" "L"))
              ((= TK_code "2241") (command "insert" "OA图框_A0_1189_竖框_大项目" pause TK_scale TK_scale 0 "" "" "explode" "L"))
              ((= TK_code "2242") (command "insert" "OA图框_A0加_1337_竖框_大项目" pause TK_scale TK_scale 0 "" "" "explode" "L"))
              ((= TK_code "2243") (command "insert" "OA图框_A0加_1486_竖框_大项目" pause TK_scale TK_scale 0 "" "" "explode" "L"))
              ((= TK_code "2244") (command "insert" "OA图框_A0加_1783_竖框_大项目" pause TK_scale TK_scale 0 "" "" "explode" "L"))
              ((= TK_code "2245") (command "insert" "OA图框_A0加_2080_竖框_大项目" pause TK_scale TK_scale 0 "" "" "explode" "L"))
              ((= TK_code "2246") (command "insert" "OA图框_A0加_2378_竖框_大项目" pause TK_scale TK_scale 0 "" "" "explode" "L"))

              ((wcmatch TK_code "##5#") (command "insert" "OA图框_A2_594_横空框" pause TK_scale TK_scale 0))
              ((wcmatch TK_code "##6#") (command "insert" "OA图框_图纸目录空表" pause TK_scale TK_scale 0))
              ((wcmatch TK_code "##7#") 
                            (if (= 1 (getint "\n类型选择（电气工程-1  智能化工程-2）："))
                                       (progn (command "-purge" "B" "OA图框_A2_594_横框_电气规范图集"  "Y"  "Y")
                                               (command "insert" "OA图框_A2_594_横框_电气规范图集" pause TK_scale TK_scale 0)
                                       )
                                       (progn (command "-purge" "B" "OA图框_A2_594_横框_智能化规范图集"  "Y"  "Y")
                                              (command "insert" "OA图框_A2_594_横框_智能化规范图集" pause TK_scale TK_scale 0)
                                       )
                             )
              )
         )
         (if (or (wcmatch TK_code "##1#")(wcmatch TK_code "##2#")(wcmatch TK_code "##3#")(wcmatch TK_code "##4#"))
              (progn (OAPUT_oneatt (entlast) "图名" "未命名")
                     (OAPUT_oneatt (entlast) "图号" "SDQ9999-999")
         ))
)


;|*****************************************************************************
OA图框工具：替换图框子功能模块 （带图名传递）
--遗留问题：标准图框和大项目图框的明确区分
|;
;;*****************************************************************************
(defun DHK_TKTH(/ OA_osm ss i en1 ss_len tk_name tk_num tk_point)
       (setq OA_osm (getvar "OSMODE"))
       (setvar "OSMODE" 0)
       (princ "\n选择需要替换的OA空图框：")
       (setq ss (ssget  '((0 . "INSERT") (2 . "*图框_A*框*"))))
       (setq ss_len (sslength ss))
       (setq i 0)
       (while (< i ss_len)
          (setq en1 (ssname ss i))
          (setq tk_name (OAGET_oneatt en1 "图名"))
          (setq tk_num (OAGET_oneatt en1 "图号"))
          (setq tk_point (OAGET_BLKPOINT en1))
          (command "erase" en1 "")
          (cond ((= TK_code "1111") (command "insert" "OA图框_A3_420_横框_标准" tk_point TK_scale TK_scale 0 "" "" "explode" "L"))
              ((= TK_code "1112") (command "insert" "OA图框_A3加_472_横框_标准" tk_point TK_scale TK_scale 0 "" "" "explode" "L"))
              ((= TK_code "1113") (command "insert" "OA图框_A3加_525_横框_标准" tk_point TK_scale TK_scale 0 "" "" "explode" "L"))
              ((= TK_code "1114") (command "insert" "OA图框_A3加_630_横框_标准" tk_point TK_scale TK_scale 0 "" "" "explode" "L"))
              ((= TK_code "1115") (command "insert" "OA图框_A3加_735_横框_标准" tk_point TK_scale TK_scale 0 "" "" "explode" "L"))
              ((= TK_code "1116") (command "insert" "OA图框_A3加_840_横框_标准" tk_point TK_scale TK_scale 0 "" "" "explode" "L"))
              ((= TK_code "1121") (command "insert" "OA图框_A2_594_横框_标准" tk_point TK_scale TK_scale 0 "" "" "explode" "L"))
              ((= TK_code "1122") (command "insert" "OA图框_A2加_668_横框_标准" tk_point TK_scale TK_scale 0 "" "" "explode" "L"))
              ((= TK_code "1123") (command "insert" "OA图框_A2加_742_横框_标准" tk_point TK_scale TK_scale 0 "" "" "explode" "L"))
              ((= TK_code "1124") (command "insert" "OA图框_A2加_891_横框_标准" tk_point TK_scale TK_scale 0 "" "" "explode" "L"))
              ((= TK_code "1125") (command "insert" "OA图框_A2加_1039_横框_标准" tk_point TK_scale TK_scale 0 "" "" "explode" "L"))
              ((= TK_code "1126") (command "insert" "OA图框_A2加_1188_横框_标准" tk_point TK_scale TK_scale 0 "" "" "explode" "L"))
              ((= TK_code "1131") (command "insert" "OA图框_A1_841_横框_标准" tk_point TK_scale TK_scale 0 "" "" "explode" "L"))
              ((= TK_code "1132") (command "insert" "OA图框_A1加_946_横框_标准" tk_point TK_scale TK_scale 0 "" "" "explode" "L"))
              ((= TK_code "1133") (command "insert" "OA图框_A1加_1051_横框_标准" tk_point TK_scale TK_scale 0 "" "" "explode" "L"))
              ((= TK_code "1134") (command "insert" "OA图框_A1加_1261_横框_标准" tk_point TK_scale TK_scale 0 "" "" "explode" "L"))
              ((= TK_code "1135") (command "insert" "OA图框_A1加_1471_横框_标准" tk_point TK_scale TK_scale 0 "" "" "explode" "L"))
              ((= TK_code "1136") (command "insert" "OA图框_A1加_1682_横框_标准" tk_point TK_scale TK_scale 0 "" "" "explode" "L"))
              ((= TK_code "1141") (command "insert" "OA图框_A0_1189_横框_标准" tk_point TK_scale TK_scale 0 "" "" "explode" "L"))
              ((= TK_code "1142") (command "insert" "OA图框_A0加_1337_横框_标准" tk_point TK_scale TK_scale 0 "" "" "explode" "L"))
              ((= TK_code "1143") (command "insert" "OA图框_A0加_1486_横框_标准" tk_point TK_scale TK_scale 0 "" "" "explode" "L"))
              ((= TK_code "1144") (command "insert" "OA图框_A0加_1783_横框_标准" tk_point TK_scale TK_scale 0 "" "" "explode" "L"))
              ((= TK_code "1145") (command "insert" "OA图框_A0加_2080_横框_标准" tk_point TK_scale TK_scale 0 "" "" "explode" "L"))
              ((= TK_code "1146") (command "insert" "OA图框_A0加_2378_横框_标准" tk_point TK_scale TK_scale 0 "" "" "explode" "L"))

              ((= TK_code "2111") (command "insert" "OA图框_A3_420_横框_大项目" tk_point TK_scale TK_scale 0 "" "" "explode" "L"))
              ((= TK_code "2112") (command "insert" "OA图框_A3加_472_横框_大项目" tk_point TK_scale TK_scale 0 "" "" "explode" "L"))
              ((= TK_code "2113") (command "insert" "OA图框_A3加_525_横框_大项目" tk_point TK_scale TK_scale 0 "" "" "explode" "L"))
              ((= TK_code "2114") (command "insert" "OA图框_A3加_630_横框_大项目" tk_point TK_scale TK_scale 0 "" "" "explode" "L"))
              ((= TK_code "2115") (command "insert" "OA图框_A3加_735_横框_大项目" tk_point TK_scale TK_scale 0 "" "" "explode" "L"))
              ((= TK_code "2116") (command "insert" "OA图框_A3加_840_横框_大项目" tk_point TK_scale TK_scale 0 "" "" "explode" "L"))
              ((= TK_code "2121") (command "insert" "OA图框_A2_594_横框_大项目" tk_point TK_scale TK_scale 0 "" "" "explode" "L"))
              ((= TK_code "2122") (command "insert" "OA图框_A2加_668_横框_大项目" tk_point TK_scale TK_scale 0 "" "" "explode" "L"))
              ((= TK_code "2123") (command "insert" "OA图框_A2加_742_横框_大项目" tk_point TK_scale TK_scale 0 "" "" "explode" "L"))
              ((= TK_code "2124") (command "insert" "OA图框_A2加_891_横框_大项目" tk_point TK_scale TK_scale 0 "" "" "explode" "L"))
              ((= TK_code "2125") (command "insert" "OA图框_A2加_1039_横框_大项目" tk_point TK_scale TK_scale 0 "" "" "explode" "L"))
              ((= TK_code "2126") (command "insert" "OA图框_A2加_1188_横框_大项目" tk_point TK_scale TK_scale 0 "" "" "explode" "L"))
              ((= TK_code "2131") (command "insert" "OA图框_A1_841_横框_大项目" tk_point TK_scale TK_scale 0 "" "" "explode" "L"))
              ((= TK_code "2132") (command "insert" "OA图框_A1加_946_横框_大项目" tk_point TK_scale TK_scale 0 "" "" "explode" "L"))
              ((= TK_code "2133") (command "insert" "OA图框_A1加_1051_横框_大项目" tk_point TK_scale TK_scale 0 "" "" "explode" "L"))
              ((= TK_code "2134") (command "insert" "OA图框_A1加_1261_横框_大项目" tk_point TK_scale TK_scale 0 "" "" "explode" "L"))
              ((= TK_code "2135") (command "insert" "OA图框_A1加_1471_横框_大项目" tk_point TK_scale TK_scale 0 "" "" "explode" "L"))
              ((= TK_code "2136") (command "insert" "OA图框_A1加_1682_横框_大项目" tk_point TK_scale TK_scale 0 "" "" "explode" "L"))
              ((= TK_code "2141") (command "insert" "OA图框_A0_1189_横框_大项目" tk_point TK_scale TK_scale 0 "" "" "explode" "L"))
              ((= TK_code "2142") (command "insert" "OA图框_A0加_1337_横框_大项目" tk_point TK_scale TK_scale 0 "" "" "explode" "L"))
              ((= TK_code "2143") (command "insert" "OA图框_A0加_1486_横框_大项目" tk_point TK_scale TK_scale 0 "" "" "explode" "L"))
              ((= TK_code "2144") (command "insert" "OA图框_A0加_1783_横框_大项目" tk_point TK_scale TK_scale 0 "" "" "explode" "L"))
              ((= TK_code "2145") (command "insert" "OA图框_A0加_2080_横框_大项目" tk_point TK_scale TK_scale 0 "" "" "explode" "L"))
              ((= TK_code "2146") (command "insert" "OA图框_A0加_2378_横框_大项目" tk_point TK_scale TK_scale 0 "" "" "explode" "L"))

              ((= TK_code "1211") (command "insert" "OA图框_A3_420_竖框_标准" tk_point TK_scale TK_scale 0 "" "" "explode" "L"))
              ((= TK_code "1212") (command "insert" "OA图框_A3加_472_竖框_标准" tk_point TK_scale TK_scale 0 "" "" "explode" "L"))
              ((= TK_code "1213") (command "insert" "OA图框_A3加_525_竖框_标准" tk_point TK_scale TK_scale 0 "" "" "explode" "L"))
              ((= TK_code "1214") (command "insert" "OA图框_A3加_630_竖框_标准" tk_point TK_scale TK_scale 0 "" "" "explode" "L"))
              ((= TK_code "1215") (command "insert" "OA图框_A3加_735_竖框_标准" tk_point TK_scale TK_scale 0 "" "" "explode" "L"))
              ((= TK_code "1216") (command "insert" "OA图框_A3加_840_竖框_标准" tk_point TK_scale TK_scale 0 "" "" "explode" "L"))
              ((= TK_code "1221") (command "insert" "OA图框_A2_594_竖框_标准" tk_point TK_scale TK_scale 0 "" "" "explode" "L"))
              ((= TK_code "1222") (command "insert" "OA图框_A2加_668_竖框_标准" tk_point TK_scale TK_scale 0 "" "" "explode" "L"))
              ((= TK_code "1223") (command "insert" "OA图框_A2加_742_竖框_标准" tk_point TK_scale TK_scale 0 "" "" "explode" "L"))
              ((= TK_code "1224") (command "insert" "OA图框_A2加_891_竖框_标准" tk_point TK_scale TK_scale 0 "" "" "explode" "L"))
              ((= TK_code "1225") (command "insert" "OA图框_A2加_1039_竖框_标准" tk_point TK_scale TK_scale 0 "" "" "explode" "L"))
              ((= TK_code "1226") (command "insert" "OA图框_A2加_1188_竖框_标准" tk_point TK_scale TK_scale 0 "" "" "explode" "L"))
              ((= TK_code "1231") (command "insert" "OA图框_A1_841_竖框_标准" tk_point TK_scale TK_scale 0 "" "" "explode" "L"))
              ((= TK_code "1232") (command "insert" "OA图框_A1加_946_竖框_标准" tk_point TK_scale TK_scale 0 "" "" "explode" "L"))
              ((= TK_code "1233") (command "insert" "OA图框_A1加_1051_竖框_标准" tk_point TK_scale TK_scale 0 "" "" "explode" "L"))
              ((= TK_code "1234") (command "insert" "OA图框_A1加_1261_竖框_标准" tk_point TK_scale TK_scale 0 "" "" "explode" "L"))
              ((= TK_code "1235") (command "insert" "OA图框_A1加_1471_竖框_标准" tk_point TK_scale TK_scale 0 "" "" "explode" "L"))
              ((= TK_code "1236") (command "insert" "OA图框_A1加_1682_竖框_标准" tk_point TK_scale TK_scale 0 "" "" "explode" "L"))
              ((= TK_code "1241") (command "insert" "OA图框_A0_1189_竖框_标准" tk_point TK_scale TK_scale 0 "" "" "explode" "L"))
              ((= TK_code "1242") (command "insert" "OA图框_A0加_1337_竖框_标准" tk_point TK_scale TK_scale 0 "" "" "explode" "L"))
              ((= TK_code "1243") (command "insert" "OA图框_A0加_1486_竖框_标准" tk_point TK_scale TK_scale 0 "" "" "explode" "L"))
              ((= TK_code "1244") (command "insert" "OA图框_A0加_1783_竖框_标准" tk_point TK_scale TK_scale 0 "" "" "explode" "L"))
              ((= TK_code "1245") (command "insert" "OA图框_A0加_2080_竖框_标准" tk_point TK_scale TK_scale 0 "" "" "explode" "L"))
              ((= TK_code "1246") (command "insert" "OA图框_A0加_2378_竖框_标准" tk_point TK_scale TK_scale 0 "" "" "explode" "L"))

              ((= TK_code "2211") (command "insert" "OA图框_A3_420_竖框_大项目" tk_point TK_scale TK_scale 0 "" "" "explode" "L"))
              ((= TK_code "2212") (command "insert" "OA图框_A3加_472_竖框_大项目" tk_point TK_scale TK_scale 0 "" "" "explode" "L"))
              ((= TK_code "2213") (command "insert" "OA图框_A3加_525_竖框_大项目" tk_point TK_scale TK_scale 0 "" "" "explode" "L"))
              ((= TK_code "2214") (command "insert" "OA图框_A3加_630_竖框_大项目" tk_point TK_scale TK_scale 0 "" "" "explode" "L"))
              ((= TK_code "2215") (command "insert" "OA图框_A3加_735_竖框_大项目" tk_point TK_scale TK_scale 0 "" "" "explode" "L"))
              ((= TK_code "2216") (command "insert" "OA图框_A3加_840_竖框_大项目" tk_point TK_scale TK_scale 0 "" "" "explode" "L"))
              ((= TK_code "2221") (command "insert" "OA图框_A2_594_竖框_大项目" tk_point TK_scale TK_scale 0 "" "" "explode" "L"))
              ((= TK_code "2222") (command "insert" "OA图框_A2加_668_竖框_大项目" tk_point TK_scale TK_scale 0 "" "" "explode" "L"))
              ((= TK_code "2223") (command "insert" "OA图框_A2加_742_竖框_大项目" tk_point TK_scale TK_scale 0 "" "" "explode" "L"))
              ((= TK_code "2224") (command "insert" "OA图框_A2加_891_竖框_大项目" tk_point TK_scale TK_scale 0 "" "" "explode" "L"))
              ((= TK_code "2225") (command "insert" "OA图框_A2加_1039_竖框_大项目" tk_point TK_scale TK_scale 0 "" "" "explode" "L"))
              ((= TK_code "2226") (command "insert" "OA图框_A2加_1188_竖框_大项目" tk_point TK_scale TK_scale 0 "" "" "explode" "L"))
              ((= TK_code "2231") (command "insert" "OA图框_A1_841_竖框_大项目" tk_point TK_scale TK_scale 0 "" "" "explode" "L"))
              ((= TK_code "2232") (command "insert" "OA图框_A1加_946_竖框_大项目" tk_point TK_scale TK_scale 0 "" "" "explode" "L"))
              ((= TK_code "2233") (command "insert" "OA图框_A1加_1051_竖框_大项目" tk_point TK_scale TK_scale 0 "" "" "explode" "L"))
              ((= TK_code "2234") (command "insert" "OA图框_A1加_1261_竖框_大项目" tk_point TK_scale TK_scale 0 "" "" "explode" "L"))
              ((= TK_code "2235") (command "insert" "OA图框_A1加_1471_竖框_大项目" tk_point TK_scale TK_scale 0 "" "" "explode" "L"))
              ((= TK_code "2236") (command "insert" "OA图框_A1加_1682_竖框_大项目" tk_point TK_scale TK_scale 0 "" "" "explode" "L"))
              ((= TK_code "2241") (command "insert" "OA图框_A0_1189_竖框_大项目" tk_point TK_scale TK_scale 0 "" "" "explode" "L"))
              ((= TK_code "2242") (command "insert" "OA图框_A0加_1337_竖框_大项目" tk_point TK_scale TK_scale 0 "" "" "explode" "L"))
              ((= TK_code "2243") (command "insert" "OA图框_A0加_1486_竖框_大项目" tk_point TK_scale TK_scale 0 "" "" "explode" "L"))
              ((= TK_code "2244") (command "insert" "OA图框_A0加_1783_竖框_大项目" tk_point TK_scale TK_scale 0 "" "" "explode" "L"))
              ((= TK_code "2245") (command "insert" "OA图框_A0加_2080_竖框_大项目" tk_point TK_scale TK_scale 0 "" "" "explode" "L"))
              ((= TK_code "2246") (command "insert" "OA图框_A0加_2378_竖框_大项目" tk_point TK_scale TK_scale 0 "" "" "explode" "L"))
         )
         (if (or (wcmatch TK_code "##1#")(wcmatch TK_code "##2#")(wcmatch TK_code "##3#")(wcmatch TK_code "##4#"))
              (progn (OAPUT_oneatt (entlast) "图名" tk_name)
                     (OAPUT_oneatt (entlast) "图号" tk_num)
         ))
         (setq i (+ 1 i))
   )
   (setvar "OSMODE" OA_osm)
)


;|*****************************************************************************
OA图框工具：图框矩阵重排（每次排一排），间距100
--全局系统变量如下：
    Meaad_all_Scale            全局比例因子 
|;
;;*****************************************************************************
(defun DHK_OATKJZCP(/ p0 p1 p2 p3 p4 xadd oldpoint newpoint OA_osm ss ss_len 
en0 vn0 i TKBLK_name)
    (setq OA_osm (getvar "OSMODE"))
    (setvar "OSMODE" 0)
    (if  (= Meaad_all_scale nil) (setq meaad_all_scale (getint "\n出图比例因数Meaad_all_scale还没有定义，请输入1：<1,100,200,1000>：")))
    (if  (= Meaad_all_scale nil) (setq meaad_all_scale 1))
    (princ "\n选取要重排的全部图纸...")
    (while  (setq ss (ssget  '((0 . "INSERT") (2 . "*图框_A*框*"))))
            (setq ss (SORT-SE (SORT-SE ss 10 0 (* 150 Meaad_all_scale) nil) 10 1 (* 150 Meaad_all_scale) T))
            (setq ss_len (sslength ss))
            (setq p0 (oaget_blkpoint (ssname ss 0)))
            (setq newpoint (getpoint "\n拾取重排单行左下角点<首个图框插入点，确保该区域没有图元！！！>:"))
            (if (= newpoint nil) (setq newpoint p0))
            (setq i 0)
            (while (< i ss_len)
               (setq en0 (ssname ss i))
               (setq vn0 (vlax-ename->vla-object en0))
               (setq TKBLK_name (vla-get-name vn0))
               (setq P1 (oaget_blkpoint en0))               
               (cond ((wcmatch TKBLK_name "*图框_A3_420_横*") 
                             (setq p2 (polar p1 0 (*  Meaad_all_Scale 420)))
                             (setq p3 (polar p1 (dtr 90)  (*  Meaad_all_Scale 297)))
                             (setq p4 (polar p2 (dtr 90)  (*  Meaad_all_Scale 297)))
                             (setq xadd (* Meaad_all_Scale 520))
                      )
                      ((wcmatch TKBLK_name "*图框_A3加_472_横*") 
                             (setq p2 (polar p1 0 (*  Meaad_all_Scale 472)))
                             (setq p3 (polar p1 (dtr 90)  (*  Meaad_all_Scale 297)))
                             (setq p4 (polar p2 (dtr 90)  (*  Meaad_all_Scale 297)))
                             (setq xadd (* Meaad_all_Scale 572))
                      )
                      ((wcmatch TKBLK_name "*图框_A3加_525_横*") 
                             (setq p2 (polar p1 0 (*  Meaad_all_Scale 525)))
                             (setq p3 (polar p1 (dtr 90)  (*  Meaad_all_Scale 297)))
                             (setq p4 (polar p2 (dtr 90)  (*  Meaad_all_Scale 297)))
                             (setq xadd (* Meaad_all_Scale 625))
                      )
                      ((wcmatch TKBLK_name "*图框_A3加_630_横*") 
                             (setq p2 (polar p1 0 (*  Meaad_all_Scale 630)))
                             (setq p3 (polar p1 (dtr 90)  (*  Meaad_all_Scale 297)))
                             (setq p4 (polar p2 (dtr 90)  (*  Meaad_all_Scale 297)))
                             (setq xadd (* Meaad_all_Scale 730))
                      )
                      ((wcmatch TKBLK_name "*图框_A3加_735_横*") 
                             (setq p2 (polar p1 0 (*  Meaad_all_Scale 735)))
                             (setq p3 (polar p1 (dtr 90)  (*  Meaad_all_Scale 297)))
                             (setq p4 (polar p2 (dtr 90)  (*  Meaad_all_Scale 297)))
                             (setq xadd (* Meaad_all_Scale 835))
                      )
                      ((wcmatch TKBLK_name "*图框_A3加_840_横*") 
                             (setq p2 (polar p1 0 (*  Meaad_all_Scale 840)))
                             (setq p3 (polar p1 (dtr 90)  (*  Meaad_all_Scale 297)))
                             (setq p4 (polar p2 (dtr 90)  (*  Meaad_all_Scale 297)))
                             (setq xadd (* Meaad_all_Scale 940))
                      )
                      ((wcmatch TKBLK_name "*图框_A2_594_横*") 
                             (setq p2 (polar p1 0 (*  Meaad_all_Scale 594)))
                             (setq p3 (polar p1 (dtr 90)  (*  Meaad_all_Scale 420)))
                             (setq p4 (polar p2 (dtr 90)  (*  Meaad_all_Scale 420)))
                             (setq xadd (* Meaad_all_Scale 694))
                      )
                      ((wcmatch TKBLK_name "*图框_A2加_668_横*") 
                             (setq p2 (polar p1 0 (*  Meaad_all_Scale 668)))
                             (setq p3 (polar p1 (dtr 90)  (*  Meaad_all_Scale 420)))
                             (setq p4 (polar p2 (dtr 90)  (*  Meaad_all_Scale 420)))
                             (setq xadd (* Meaad_all_Scale 768))
                      )
                      ((wcmatch TKBLK_name "*图框_A2加_742_横*") 
                             (setq p2 (polar p1 0 (*  Meaad_all_Scale 742)))
                             (setq p3 (polar p1 (dtr 90)  (*  Meaad_all_Scale 420)))
                             (setq p4 (polar p2 (dtr 90)  (*  Meaad_all_Scale 420)))
                             (setq xadd (* Meaad_all_Scale 842))
                      )
                      ((wcmatch TKBLK_name "*图框_A2加_891_横*") 
                             (setq p2 (polar p1 0 (*  Meaad_all_Scale 891)))
                             (setq p3 (polar p1 (dtr 90)  (*  Meaad_all_Scale 420)))
                             (setq p4 (polar p2 (dtr 90)  (*  Meaad_all_Scale 420)))
                             (setq xadd (* Meaad_all_Scale 991))
                      )
                      ((wcmatch TKBLK_name "*图框_A2加_1039_横*") 
                             (setq p2 (polar p1 0 (*  Meaad_all_Scale 1039)))
                             (setq p3 (polar p1 (dtr 90)  (*  Meaad_all_Scale 420)))
                             (setq p4 (polar p2 (dtr 90)  (*  Meaad_all_Scale 420)))
                             (setq xadd (* Meaad_all_Scale 1139))
                      )
                      ((wcmatch TKBLK_name "*图框_A2加_1188_横*") 
                             (setq p2 (polar p1 0 (*  Meaad_all_Scale 1188)))
                             (setq p3 (polar p1 (dtr 90)  (*  Meaad_all_Scale 420)))
                             (setq p4 (polar p2 (dtr 90)  (*  Meaad_all_Scale 420)))
                             (setq xadd (* Meaad_all_Scale 1288))
                      )
                      ((wcmatch TKBLK_name "*图框_A1_841_横*") 
                             (setq p2 (polar p1 0 (*  Meaad_all_Scale 841)))
                             (setq p3 (polar p1 (dtr 90)  (*  Meaad_all_Scale 594)))
                             (setq p4 (polar p2 (dtr 90)  (*  Meaad_all_Scale 594)))
                             (setq xadd (* Meaad_all_Scale 941))
                      )
                      ((wcmatch TKBLK_name "*图框_A1加_946_横*") 
                             (setq p2 (polar p1 0 (*  Meaad_all_Scale 946)))
                             (setq p3 (polar p1 (dtr 90)  (*  Meaad_all_Scale 594)))
                             (setq p4 (polar p2 (dtr 90)  (*  Meaad_all_Scale 594)))
                             (setq xadd (* Meaad_all_Scale 1046))
                      )
                      ((wcmatch TKBLK_name "*图框_A1加_1051_横*") 
                             (setq p2 (polar p1 0 (*  Meaad_all_Scale 1051)))
                             (setq p3 (polar p1 (dtr 90)  (*  Meaad_all_Scale 594)))
                             (setq p4 (polar p2 (dtr 90)  (*  Meaad_all_Scale 594)))
                             (setq xadd (* Meaad_all_Scale 1151))
                      )
                      ((wcmatch TKBLK_name "*图框_A1加_1261_横*") 
                             (setq p2 (polar p1 0 (*  Meaad_all_Scale 1261)))
                             (setq p3 (polar p1 (dtr 90)  (*  Meaad_all_Scale 594)))
                             (setq p4 (polar p2 (dtr 90)  (*  Meaad_all_Scale 594)))
                             (setq xadd (* Meaad_all_Scale 1361))
                      )
                      ((wcmatch TKBLK_name "*图框_A1加_1471_横*") 
                             (setq p2 (polar p1 0 (*  Meaad_all_Scale 1471)))
                             (setq p3 (polar p1 (dtr 90)  (*  Meaad_all_Scale 594)))
                             (setq p4 (polar p2 (dtr 90)  (*  Meaad_all_Scale 594)))
                             (setq xadd (* Meaad_all_Scale 1571))
                      )
                      ((wcmatch TKBLK_name "*图框_A1加_1682_横*") 
                             (setq p2 (polar p1 0 (*  Meaad_all_Scale 1682)))
                             (setq p3 (polar p1 (dtr 90)  (*  Meaad_all_Scale 594)))
                             (setq p4 (polar p2 (dtr 90)  (*  Meaad_all_Scale 594)))
                             (setq xadd (* Meaad_all_Scale 1782))
                      )
                      ((wcmatch TKBLK_name "*图框_A0_1189_横*") 
                             (setq p2 (polar p1 0 (*  Meaad_all_Scale 1189)))
                             (setq p3 (polar p1 (dtr 90)  (*  Meaad_all_Scale 841)))
                             (setq p4 (polar p2 (dtr 90)  (*  Meaad_all_Scale 841)))
                             (setq xadd (* Meaad_all_Scale 1289))
                      )
                      ((wcmatch TKBLK_name "*图框_A0加_1337_横*") 
                             (setq p2 (polar p1 0 (*  Meaad_all_Scale 1337)))
                             (setq p3 (polar p1 (dtr 90)  (*  Meaad_all_Scale 841)))
                             (setq p4 (polar p2 (dtr 90)  (*  Meaad_all_Scale 841)))
                             (setq xadd (* Meaad_all_Scale 1437))
                      )
                      ((wcmatch TKBLK_name "*图框_A0加_1486_横*") 
                             (setq p2 (polar p1 0 (*  Meaad_all_Scale 1486)))
                             (setq p3 (polar p1 (dtr 90)  (*  Meaad_all_Scale 841)))
                             (setq p4 (polar p2 (dtr 90)  (*  Meaad_all_Scale 841)))
                             (setq xadd (* Meaad_all_Scale 1586))
                      )
                      ((wcmatch TKBLK_name "*图框_A0加_1783_横*") 
                             (setq p2 (polar p1 0 (*  Meaad_all_Scale 1783)))
                             (setq p3 (polar p1 (dtr 90)  (*  Meaad_all_Scale 841)))
                             (setq p4 (polar p2 (dtr 90)  (*  Meaad_all_Scale 841)))
                             (setq xadd (* Meaad_all_Scale 1883))
                      )
                      ((wcmatch TKBLK_name "*图框_A0加_2080_横*") 
                             (setq p2 (polar p1 0 (*  Meaad_all_Scale 2080)))
                             (setq p3 (polar p1 (dtr 90)  (*  Meaad_all_Scale 841)))
                             (setq p4 (polar p2 (dtr 90)  (*  Meaad_all_Scale 841)))
                             (setq xadd (* Meaad_all_Scale 2180))
                      )
                      ((wcmatch TKBLK_name "*图框_A0加_2378_横*") 
                             (setq p2 (polar p1 0 (*  Meaad_all_Scale 2378)))
                             (setq p3 (polar p1 (dtr 90)  (*  Meaad_all_Scale 841)))
                             (setq p4 (polar p2 (dtr 90)  (*  Meaad_all_Scale 841)))
                             (setq xadd (* Meaad_all_Scale 2478))
                      )
                   )
                  (command "move" "w" p1 p4 "" p1 newpoint)
                  (setq newpoint (polar newpoint 0 xadd))
                  (setq i (+ i 1))
               )
         )
       (setvar "OSMODE" OA_osm)
)






;|*****************************************************************************
工程设计信息编辑DCL对话框响应主程序
--输出文件保存在“软件安装目录”下的“工程信息”目录下
--引用全局系统变量如下：
    MEAAD_AZML_V31                 软件安装目录
|;
;;*****************************************************************************
(DEFUN DHK_OAGCXXZS (/ dd dcl_EAAD)
   (if (= MEAAD_AZML_V31 nil) 
            (progn  (alert "软件安装位置全局变量MEAAD_AZML_V31没有定义!") (exit)))
    (setq dcl_EAAD (load_dialog "Meaad_OATK_3.0.dcl"))
    (if (not  (new_dialog "MEAAD3_OA_Project1" dcl_EAAD))  (exit))  
    (set_tile "PJ_SGTSJ" "1")
    (set_tile "PJ_DQZY" "1")
    (setq dd 9)
    (action_tile "DHK_PJ_READFILE" "(DHK_PJRDFILE)(DHK_PJSET)")
    (action_tile "DHK_PJ_READATT" "(done_dialog 1)  (unload_dialog dcl_EAAD)")
    (action_tile "DHK_PJ_OUTPUT" "(DHK_PJOUTFILE)")
    (action_tile "DHK_PJ_MLXZ" "(DHK_PJRDDCL) (done_dialog 2) (unload_dialog dcl_EAAD)")
    (action_tile "DHK_PJ_DWGOUT" "(done_dialog 3) (unload_dialog dcl_EAAD)")
    (action_tile "cancel" "(done_dialog 0)  (unload_dialog dcl_EAAD)")
    (setq dd (start_dialog))
    (while (= dd 1)
                (DHK_PJRDATT) 
                (setq dcl_EAAD (load_dialog "Meaad_OATK_3.0.dcl"))
                (new_dialog "MEAAD3_OA_Project1" dcl_EAAD)
                (DHK_PJSET)
                (action_tile "DHK_PJ_READFILE" "(DHK_PJRDFILE)(DHK_PJSET)")
                (action_tile "DHK_PJ_READATT" "(done_dialog 1)  (unload_dialog dcl_EAAD)")
                (action_tile "DHK_PJ_OUTPUT" "(DHK_PJOUTFILE)")
                (action_tile "DHK_PJ_MLXZ" "(DHK_PJRDDCL) (done_dialog 2)  (unload_dialog dcl_EAAD)")
                (action_tile "DHK_PJ_DWGOUT" "(done_dialog 3) (unload_dialog dcl_EAAD)")
                (action_tile "cancel" "(done_dialog 0) (unload_dialog dcl_EAAD)")
                (setq dd (start_dialog))
    )
    (cond 
           ((= dd 2) (DHK_PJMLXZ))
           ((= dd 3) (DHK_PJDWGOUT))
    )
)
   




;|*****************************************************************************
工程设计信息编辑DCL对话框功能子程序:DCL数据从文件读取
|;
;;***************************************************************************** 
(defun DHK_PJRDFILE(/ PJXX_file fi)
        (setq PJXX_file (getfiled "打开 工程信息 文件" (strcat MEAAD_AZML_V31 "工程信息3.0\\Project1") "PRJ" 2))
	(setq fi (open PJXX_file "r"))
	(setq PJ-name (read-line fi))
	(setq PJ-item (read-line fi))
	(setq PJ-volume (read-line fi))
	(setq PJ-code (read-line fi))
	(setq PJ-vnum (read-line fi))
	(setq PJ-cnum (read-line fi))
	(setq PJ-date (read-line fi))
	(setq PJ-jd (read-line fi))
	(setq PJ-zy (read-line fi))
	(close fi)
        (print (list PJ-name PJ-item PJ-volume PJ-volume PJ-code PJ-vnum PJ-cnum PJ-date PJ-jd PJ-zy))
        (print)
)

;|*****************************************************************************
工程设计信息编辑DCL对话框功能子程序:DCL数据设置
|;
;;***************************************************************************** 
(defun DHK_PJSET()
        (set_tile "PJ_NAME" PJ-name)
        (set_tile "PJ_ITEM" PJ-item)
        (set_tile "PJ_VOLUME" PJ-volume)
        (set_tile "PJ_CODE" PJ-code)
        (set_tile "PJ_VNUM" PJ-vnum)
        (set_tile "PJ_CNUM" PJ-cnum)
        (set_tile "PJ_DATE" PJ-date)
        (if  (= PJ-jd "1") 
             (set_tile "PJ_CBSJ" "1")
             (set_tile "PJ_SGTSJ" "1")
        )
        (if  (= PJ-zy "1") 
             (set_tile "PJ_DQZY" "1")
             (set_tile "PJ_ZKZY" "1")
        )
)         

;|*****************************************************************************
工程设计信息编辑DCL对话框功能子程序:DCL数据输出到文件
|;
;;***************************************************************************** 
(defun DHK_PJOUTFILE(/ PJ-name PJ-item PJ-volume PJ-code PJ-vnum PJ-cnum PJ-date PJ-jd PJ-zy PJXX_file file today_time PJJZY newoutfile)
	(setq PJ-name  (get_tile "PJ_NAME"))
	(setq PJ-item (get_tile "PJ_ITEM"))
	(setq PJ-volume (get_tile "PJ_VOLUME"))
	(setq PJ-code  (get_tile "PJ_CODE"))
	(setq PJ-vnum (get_tile "PJ_VNUM"))
	(setq PJ-cnum (get_tile "PJ_CNUM"))
	(setq PJ-date (get_tile "PJ_DATE"))
	(if (= "1" (get_tile "PJ_CBSJ")) (setq PJ-jd "1") (setq PJ-jd "2"))
	(if (= "1" (get_tile "PJ_DQZY")) (setq PJ-zy "1" PJJZY "电气") (setq PJ-zy "2" PJJZY "自控"))
        (setq today_time (strcat (itoa (fix (getvar 'cdate))) (itoa (fix (*(- (getvar"cdate") (fix(getvar"cdate"))) 1000000)))))
        (setq newoutfile (strcat PJ-name "_" PJJZY "_" today_time))
        (setq PJXX_file (getfiled "输出 工程信息 文件" (strcat MEAAD_AZML_V31 "工程信息3.0\\" newoutfile) "PRJ" 1))
        (setq file (open PJXX_file "w"))
        (write-line PJ-name file)
        (write-line PJ-item file)
        (write-line PJ-volume file)
        (write-line PJ-code file)
        (write-line PJ-vnum file)
        (write-line PJ-cnum file)
        (write-line PJ-date file)
        (write-line PJ-jd file)
        (write-line PJ-zy file)
        (close file)
)


;|*****************************************************************************
工程设计信息编辑DCL对话框功能子程序:读取属性块（目录或图框参数）
|;
;;***************************************************************************** 
(defun DHK_PJRDATT (/ en0  vn0 BBname PJ-dwgnum PJ-sjjd)
        (setq en0 (car (entsel)))
        (setq vn0 (vlax-ename->vla-object en0))
        (setq BBname (vlax-get-property vn0 'Name))
        (cond ((wcmatch bbname "标准图框_*")
	        (setq PJ-name  (OAget_OneATT en0 "工程名称"))
	        (setq PJ-item (OAget_OneATT en0 "子项"))
	        (setq PJ-sjjd (OAget_OneATT en0 "设计阶段"))
	        (setq PJ-code  (OAget_OneATT en0 "设计号"))
               ;(setq PJ-sjzy (OAget_OneATT en0 "专业"))
	        (setq PJ-date (OAget_OneATT en0 "日期"))
	        (setq PJ-dwgnum (OAget_OneATT en0 "图号"))
                (cond ((= "初步设计" PJ-sjjd) (setq PJ-jd "1"))
                      ((= "施工图"  PJ-sjjd) (setq PJ-jd "2"))
                 )
                (cond ((= "DQ" (substr PJ-dwgnum 2 2)) (setq PJ-zy "1"))
                      ((= "ZK" (substr PJ-dwgnum 2 2)) (setq PJ-zy "2"))
                )
                (setq PJ-volume "")
                (setq PJ-vnum (substr PJ-dwgnum 4 2))
                (setq PJ-cnum (substr PJ-dwgnum 6 2))
              )
             ((wcmatch bbname "OA图框_图纸目录空表")
	        (setq PJ-name  (OAget_OneATT en0 "工程名称"))
	        (setq PJ-item (OAget_OneATT en0 "子项"))
	        (setq PJ-sjjd (OAget_OneATT en0 "设计阶段"))
	        (setq PJ-code  (OAget_OneATT en0 "设计号"))
	        (setq PJ-date (OAget_OneATT en0 "年份"))
	        (setq PJ-date (strcat PJ-date (OAget_OneATT en0 "月份")))
                (cond ((= "初步设计" PJ-sjjd) (setq PJ-jd "1"))
                      ((= "施工图"  PJ-sjjd) (setq PJ-jd "2"))
                 )
                (setq PJ-volume (OAget_OneATT en0 "卷册名称"))
                (if (wcmatch PJ-volume "*电气*") (setq PJ-zy "1") (setq PJ-zy "2")) 
                (setq PJ-vnum  (OAget_OneATT en0 "卷号"))
                (setq PJ-cnum  (OAget_OneATT en0 "册号"))
              )
         )
)


;|*****************************************************************************
工程设计信息编辑DCL对话框功能子程序:读取DCL文本框参数
|;
;;***************************************************************************** 
(defun DHK_PJRDDCL ()
	(setq PJ-name  (get_tile "PJ_NAME"))
	(setq PJ-item (get_tile "PJ_ITEM"))
	(setq PJ-volume (get_tile "PJ_VOLUME"))
	(setq PJ-code  (get_tile "PJ_CODE"))
	(setq PJ-vnum (get_tile "PJ_VNUM"))
	(setq PJ-cnum (get_tile "PJ_CNUM"))
	(setq PJ-date (get_tile "PJ_DATE"))
        (setq PJ-Year (substr PJ-date 1 4))
        (setq PJ-Month (substr PJ-date 5 2))
	(if (= "1" (get_tile "PJ_CBSJ")) (setq PJ-jd "初步设计") (setq PJ-jd "施工图"))
	(if (= "1" (get_tile "PJ_DQZY")) (setq PJ-zy "电气") (setq PJ-zy "自控"))
)




;|*****************************************************************************
工程设计信息编辑DCL对话框功能子程序:目录头信息修正，可多页
--引用（DHK_PJRDDCL）输出变量
|;
;;*****************************************************************************
(defun DHK_PJMLXZ (/ SS i PJ-NSUM en PJ-NXH)
	     (princ "\n点取要修改的属性块...")
	     (setq SS (ssget '((0 . "INSERT") (2 . "OA图框_图纸目录空表"))))
	     (setq i 0)
             (setq ss (SORT-SE SS 10 0 10.0 NIL))
             (setq PJ-NSUM (sslength ss))
             (repeat (sslength ss)
                 (setq en (ssname ss i))
                 (setq PJ-NXH (itoa (+ i 1)))
                 (OAput_OneATT en "工程名称" PJ-name)
                 (OAput_oneatt en "子项" PJ-item) 
                 (OAput_oneatt en "设计阶段" PJ-jd)
                 (OAput_oneatt en "卷册名称" PJ-volume)
                 (OAput_oneatt en "设计号" PJ-code)
                 (OAput_oneatt en "卷号" PJ-vnum)
                 (OAput_oneatt en "册号" PJ-cnum)
                 (OAput_oneatt en "年份" PJ-Year)
                 (OAput_oneatt en "月份" PJ-Month)
                 (OAput_oneatt en "目录页总数" (itoa PJ-NSUM))
                 (OAput_oneatt en "目录序号"  PJ-NXH)
                 (setq i (+ i 1))
              )
)

;|*****************************************************************************
工程设计信息编辑DCL对话框功能子程序:目录属性导出为文本文件，供初设目录导出
--引用（DHK_PJRDDCL）输出变量
20200403
|;
;;*****************************************************************************
(defun DHK_PJDWGOUT (/ ss p en en0 h1 bl len i p1 p2 p3 p4 PJ_nsum MLXH MLMC MLTH MLZS)
	     (princ "\n点取要导出的目录...")
	     (setq SS (ssget '((0 . "INSERT") (2 . "OA图框_图纸目录单行"))))
	     (princ "\n点取目标位置起始点...")
	     (setq P (getpoint))
             (setq en0 (ssname ss 0))
             (setq h1 (OAget_oneatt_zbv en0 "图纸名称" 40))
             (setq bl (/  h1 4))
             (setq len (* bl 9.6))
             (setq SS (SORT-SE (SORT-SE SS 10 1 (* bl 3) nil) 10 0 (* bl 100) nil))
	     (setq i 0)
             (setq PJ-NSUM (sslength ss))
             (setq p1 (polar p 0 (* bl 6)))
             (setq p2 (polar p 0 (* bl 15)))
             (setq p3 (polar p 0 (* bl 100)))
             (setq p4 (polar p 0 (* bl 155)))
             (repeat PJ-NSUM
                 (setq en (ssname ss i))
                 (setq MLXH  (OAget_OneATT en "序号"))
                 (setq MLMC  (OAget_OneATT en "图纸名称"))
                 (setq MLTH  (OAget_OneATT en "图纸图号"))
                 (setq MLZS  (OAget_OneATT en "张数"))
                 (command "text" "s" "sj2ydq_文本" p1 h1 0 MLXH)
                 (command "text" "s" "sj2ydq_文本" p2 h1 0 MLMC)
                 (command "text" "s" "sj2ydq_文本" p3 h1 0 MLTH)
                 (command "text" "s" "sj2ydq_文本" p4 h1 0 MLZS) 
                 (setq p1 (polar P1 (dtr 270) len))
                 (setq p2 (polar P2 (dtr 270) len))
                 (setq p3 (polar P3 (dtr 270) len))
                 (setq p4 (polar P4 (dtr 270) len))         
                 (setq i (+ i 1))
              )
)




;|*****************************************************************************
工程设计OA图框DCL对话框功能子程序:初始目录生成
20200330
--引用全局变量   Meaad_all_scale
|;
;;*****************************************************************************
(defun DHK_OACSMLSC(/ OA_osm num i n p0 p2 p3)
    (setq OA_osm (getvar "OSMODE"))
    (setvar "OSMODE" 0)
    (setq num "")
    (setq i 0)
    (setq n  1)
    (setq p0 (getpoint "\n请输入目录图框左下角插入点:"))
    (if  (= Meaad_all_scale nil) (setq meaad_all_scale (getint "\n出图比例因数Meaad_all_scale还没有定义，请输入1：<1,100,200,1000>：")))
    (if  (= Meaad_all_scale nil) (setq meaad_all_scale 1))
    (repeat 5
         (command "insert" "OA图框_A2_594_横空框" p0 Meaad_all_scale Meaad_all_scale 0)
         (setq p2 (polar p0 0 (*  Meaad_all_scale 59.75)))
         (setq p2 (polar p2 (dtr 90) (*  Meaad_all_scale 372.6)))
         (command "insert" "OA图框_图纸目录空表" p2 Meaad_all_scale Meaad_all_scale 0)
         (setq p3 (polar p2 0 (*  Meaad_all_scale 12)))
         (setq p3 (polar p3 (dtr 270) (*  Meaad_all_scale 66)))
         (repeat 28
             (command "insert" "OA图框_图纸目录单行" p3 Meaad_all_scale Meaad_all_scale 0)
             (cond ((< n 10) (setq tuhao (strcat "SZY9999-00" (itoa n))))
                   ((< n 100) (setq tuhao (strcat "SZY9999-0" (itoa n))))
                   (t (setq tuhao (strcat "SZY9999-" (itoa n))))
             )
             (OAput_OneATT (entlast) "序号" (itoa n))
             (OAput_OneATT (entlast) "图纸图号" tuhao)
             (setq n (+ 1 n))
             (setq P3 (polar p3 (dtr 270) (*  Meaad_all_scale 9.6)))
         )
         (setq p2 (polar p2 0 (*  Meaad_all_scale 279.5)))
         (command "insert" "OA图框_图纸目录空表" p2 Meaad_all_scale Meaad_all_scale 0)
         (setq p3 (polar p2 0 (*  Meaad_all_scale 12)))
         (setq p3 (polar p3 (dtr 270) (*  Meaad_all_scale 66)))
         (repeat 28
             (command "insert" "OA图框_图纸目录单行" p3 Meaad_all_scale Meaad_all_scale 0)
             (cond ((< n 10) (setq tuhao (strcat "SZY9999-00" (itoa n))))
                   ((< n 100) (setq tuhao (strcat "SZY9999-0" (itoa n))))
                   (t (setq tuhao (strcat "SZY9999-" (itoa n))))
             )
             (OAput_OneATT (entlast) "序号" (itoa n))
             (OAput_OneATT (entlast) "图纸图号" tuhao)
             (setq n (+ 1 n))
             (setq P3 (polar p3 (dtr 270) (*  Meaad_all_scale 9.6)))
         )
         (setq p0 (polar p0 0 (*  Meaad_all_scale 644))) 
         (setq i (+ 56 i))
    )
    (setvar "OSMODE" OA_osm)
)

;|*****************************************************************************
工程设计OA图框DCL对话框功能子程序:目录全局刷新
20200331
--引用全局变量   Meaad_all_scale
|;
;;*****************************************************************************
(defun DHK_OAMLQJSX(/ OA_osm ss1 ss2 ss3 i1 i2 dwgdesigner dwgchecker en1 dwgnum1 stwz
num1 nn2 en2 dwgnum2 num2 pagenum2 dwgname2 dwgver2 vn2 blkname2 dwgtype2 mtgkb mtlen
dwgpoint2 dwgpoint2a en3 dwgnum3 )
    (setq OA_osm (getvar "OSMODE"))
    (setvar "OSMODE" 0)
    (if  (= Meaad_all_scale nil) (setq meaad_all_scale (getint "\n出图比例因数Meaad_all_scale还没有定义，请输入1：<1,100,200,1000>：")))
    (if  (= Meaad_all_scale nil) (setq meaad_all_scale 1))
    (princ "\n选取要刷新的全部目录...")
    (setq SS1 (ssget '((0 . "INSERT") (2 . "OA图框_图纸目录单行"))))
    (setq i1 0)
    (princ "\n选取要目录归档的图纸...")
    (while (/= (setq SS2 (ssget '((0 . "INSERT") (2 . "标准图框_A*")))) nil)
        (setq i2 0)
        (setq dwgdesigner (getstring "\n设计人："))
        (setq dwgchecker  (getstring "\n校核人："))
        (repeat (sslength ss1)
           (setq en1 (ssname ss1 i1))
           (setq dwgnum1 (OAget_OneATT en1 "图纸图号"))
           (setq stwz (vl-string-search "-" dwgnum1))
           (setq num1 (substr dwgnum1 (+ 2 stwz) 3))
           (setq nn2 (sslength ss2))
           (while (< i2 nn2)
                 (setq en2 (ssname ss2 i2))
                 (setq dwgnum2 (OAget_OneATT en2 "图号"))
                 (setq stwz (vl-string-search "-" dwgnum2))
                 (setq num2 (substr dwgnum2 (+ 2 stwz) 3))
                 (if (= num1 num2) 
                          (progn
                              (setq i2 nn2)
                              (setq pagenum2 (substr dwgnum2 (+ 9 stwz) 2))
                              (if (= pagenum2 "") (setq pagenum2  "1") (setq  pagenum2 (itoa (atoi pagenum2))))
                              (setq dwgname2 (OAget_OneATT en2 "图名"))
                              (setq dwgver2 (strcat (OAget_OneATT en2 "版本") "版"))
                              (setq vn2 (vlax-ename->vla-object en2))
                              (setq blkname2 (vla-get-name vn2))
                              (if (/= nil (vl-string-search "_横框" blkname2))
                                         (setq dwgtype2 (vl-string-search "_横框" blkname2))
                                         (setq dwgtype2 (vl-string-search "_竖框" blkname2)) 
                               )
                              (setq dwgtype2 (substr blkname2 10 (- dwgtype2 9)))
                              (setq dwgtype2 (vl-string-subst "" "加" dwgtype2))
                              (setq dwgpoint2 (OAGET_BLKPoint en2))
                              (setq dwgpoint2a (polar dwgpoint2 0 (* Meaad_all_scale 594)))
                              (setq dwgpoint2a (polar dwgpoint2a (dtr 90) (* Meaad_all_scale 420)))
                              (setq SS3 (ssget "w" dwgpoint2 dwgpoint2a '((0 . "INSERT") (2 . "OA图框_二次图标签")))) 
                              (if (/= ss3 nil) (progn
                                                   (setq en3 (ssname ss3 0))
                                                   (setq dwgnum3 (OAget_OneATT en3 "二次图号"))
                                               )
                                               (setq dwgnum3 "")
                              )
                              (setq dwgname2 (stripmt dwgname2))
                              (setq dwgname2 (vl-string-subst "" "\\P" dwgname2))
                              (setq mtlen (strlen dwgname2)) 
                              (if (> mtlen 48) 
                                   (progn
                                     (setq mtgkb (/ (* 48.0 0.8) mtlen))
                                     (OAPUT_oneatt_ZBV en1 "图纸名称" 41 mtgkb)
                              ))
                              (OAput_OneATT en1 "图纸图号" (substr dwgnum2 1 (+ 4 stwz)))
                              (OAput_OneATT en1 "图纸名称" dwgname2)
                              (OAput_OneATT en1 "二次图号" dwgnum3)
                              (OAput_OneATT en1 "张数" pagenum2)
                              (OAput_OneATT en1 "图纸版号" dwgver2)
                              (OAput_OneATT en1 "图幅" dwgtype2) 
                              (OAput_OneATT en1 "图纸设计人" dwgdesigner)
                              (OAput_OneATT en1 "图纸校核人" dwgchecker)
                           )
                           (setq i2 (+ 1 i2))
                  )
           )
           (setq i2 0)
           (setq i1 (+ 1 i1))
         )
        (setq i1 0)
        (princ "\n选取要目录归档的图纸...")
    )
   (setvar "OSMODE" OA_osm)
)



;|*****************************************************************************
工程设计OA图框DCL对话框功能子程序:目录局部调整，插入或删除连续的图纸
20200401
--引用全局变量   Meaad_all_scale
|;
;;*****************************************************************************
(defun  DHK_OAMLJBTZ(/ OA_osm SS  SUM_n i jj jj_stnum jj_num en last_p last_dwgnum n n_sy hh dwms 
SUM2_n del_ss i1 i2 ss2 en1 en2 newpoint oldpoint newxh newdwgnum uuu Tzname ppp dthst dstn)
    (setq OA_osm (getvar "OSMODE"))
    (setvar "OSMODE" 0)
    (if  (= Meaad_all_scale nil) (setq meaad_all_scale (getint "\n出图比例因数Meaad_all_scale还没有定义，请输入1：<1,100,200,1000>：")))
    (if  (= Meaad_all_scale nil) (setq meaad_all_scale 1))
    (princ "\n选取要刷新的全部目录...")
    (setq SS (ssget '((0 . "INSERT") (2 . "OA图框_图纸目录单行")))) 
    (setq SUM_n (sslength ss))
    ;;先y后x排序：
    ;(setq SS (SORT-SE (SORT-SE SS 10 1 100 nil) 10 0 2 T))
    ;(setq SS (SORT-SE (SORT-SE SS 10 0 100 nil) 10 1 2 T)
    ;(setq SS  (SORT-SE SS 10 1 2 T))
    (setq SS (SORT-SE (SORT-SE SS 10 1 (* meaad_all_scale 3) nil) 10 0 (* meaad_all_scale 100) nil));先y由小到大，再x由小到大
    (setq i 0)
    (setq jj (getint "\n调整类型 1-新增图纸 2-减少图纸 3-删除空白图 <3>："))
    (if (= jj nil) (setq jj 3))
    (cond ((= jj 3)
              (setq del_ss (ssadd)) 
              (repeat SUM_n
                    (setq en (ssname ss i))
                    (setq Tzname  (OAget_OneATT en "图纸名称"))
                    (if (= tzname "未命名图纸名称") (setq del_ss (ssadd en del_ss)))
                    (setq i (+ 1 i))
             )
             (command "erase" del_ss "")
          )
         ((= jj 1)
            (setq jj_stnum (getint "\n输入插入图纸的起始图号序号:"))
            (setq jj_num (getint "\n插入张数："))
            (setq del_ss (ssadd)) 
            (setq i 0)
            (repeat SUM_n
                    (setq en (ssname ss i))
                    (if (>= i (- jj_stnum 1))
                               (setq del_ss (ssadd en del_ss))
                     )
                    (setq i (+ 1 i))
             )
             (setq i1 (- jj_stnum 1))
             (setq i2 (- (+ jj_stnum jj_num) 1))
             (setq ss2 (ssadd))
             (repeat (+ 1 (- SUM_n jj_num jj_stnum))
                 (setq en1 (ssname ss i1))
                 (setq en2 (ssname ss i2))
                 (setq newpoint (OAGET_BLKPoint en2))
                 (setq oldpoint (OAGET_BLKPoint en1)) 
                 (setq newxh (OAget_OneATT en2 "序号"))
                 (setq newdwgnum (OAget_OneATT en2 "图纸图号")) 
                 (setq uuu (ssadd en1 ss2))
                 (command "copy" uuu "" oldpoint newpoint) 
                 (OAput_OneATT (entlast) "图纸图号" newdwgnum)
                 (OAput_OneATT (entlast) "序号" newxh)
                 (setq i1 (+ 1 i1) i2 (+ 1 i2))
                 (setq ss2 (ssadd))
             )
             (setq i2 (- jj_stnum 1))
             (setq ss2 (ssadd))
             (repeat jj_num
                 (setq en2 (ssname ss i2))
                 (setq newpoint (OAGET_BLKPoint en2)) 
                 (setq newxh (OAget_OneATT en2 "序号"))
                 (setq newdwgnum (OAget_OneATT en2 "图纸图号"))
                 (command "insert" "OA图框_图纸目录单行" newpoint Meaad_all_scale Meaad_all_scale 0)
                  (OAput_OneATT (entlast) "图纸图号" newdwgnum)
                  (OAput_OneATT (entlast) "序号" newxh)
                  (setq i2 (+ 1 i2))
             )
             (command "erase" del_ss "")
          )     
          ((= jj 2)
              (setq jj_stnum (getint "\n输入删除图纸的起始图纸序号:"))
              (setq jj_num (getint "\n删除张数："))
              (setq del_ss (ssadd)) 
              (repeat SUM_n
                    (setq en (ssname ss i))
                    (if (>= i (- jj_stnum 1))
                               (setq del_ss (ssadd en del_ss))
                     )
                    (setq i (+ 1 i))
             )
             (setq i1 (- jj_stnum 1))
             (setq i2 (- (+ jj_stnum jj_num) 1))
             (setq ss2 (ssadd))
             (repeat (- (sslength del_ss) jj_num)
                 (setq en1 (ssname ss i1))
                 (setq en2 (ssname ss i2))
                 (setq newpoint (OAGET_BLKPoint en1))
                 (setq oldpoint (OAGET_BLKPoint en2)) 
                 (setq newxh (OAget_OneATT en1 "序号"))
                 (setq newdwgnum (OAget_OneATT en1 "图纸图号")) 
                 (setq uuu (ssadd en2 ss2))
                 (command "copy" uuu "" oldpoint newpoint) 
                 (OAput_OneATT (entlast) "图纸图号" newdwgnum)
                 (OAput_OneATT (entlast) "序号" newxh)
                 (setq i1 (+ 1 i1) i2 (+ 1 i2))  
                 (setq ss2 (ssadd))
             )
             (command "erase" del_ss "")
             (setq dthst (substr newdwgnum 1 8))
             (setq dstn (+ 1 (atoi (substr newdwgnum 9))))
             (setq ppp newpoint)
             (repeat jj_num
                  (setq ppp (polar ppp  (dtr 270) (* 9.6 Meaad_all_scale)))
                  (command "insert" "OA图框_图纸目录单行" ppp Meaad_all_scale Meaad_all_scale 0)
                  (cond ((< dstn 10) (setq tuhao (strcat dthst "00" (itoa dstn))))
                      ((< dstn 100) (setq tuhao (strcat dthst "0" (itoa dstn))))
                      (t (setq tuhao (strcat dthst (itoa dstn))))
                   )
                  (OAput_OneATT (entlast) "图纸图号" tuhao)
                  (OAput_OneATT (entlast) "序号" (itoa dstn))
                  (setq dstn (+ 1 dstn))
             )
       )
    )
   (setvar "OSMODE" OA_osm)
)


;|*****************************************************************************
工程设计OA图框DCL对话框功能子程序:二次原理图（参考通用）的提取及目录集成对话框主程序
20200403
--引用全局变量   Meaad_all_scale  MEAAD_AZML_V31 
|;
;;*****************************************************************************
(DEFUN DHK_OACKTJSX (/ dcl_EAAD today_time)
    (if  (= Meaad_all_scale nil) (setq meaad_all_scale (getint "\n出图比例因数Meaad_all_scale还没有定义，请输入1：<1,100,200,1000>：")))
    (if  (= Meaad_all_scale nil) (setq meaad_all_scale 1))
    (if (= MEAAD_AZML_V31 nil) 
            (progn  (alert "软件安装位置全局变量MEAAD_AZML_V31没有定义!") (exit)))
    (setq dcl_EAAD (load_dialog "Meaad_OATK_3.0.dcl"))
    (if (not  (new_dialog "MEAAD3_OA_ERCKTJ" dcl_EAAD))  (exit))
    (setq today_time (strcat (itoa (fix (getvar 'cdate))) (itoa (fix (*(- (getvar"cdate") (fix(getvar"cdate"))) 1000000)))))
    (set_tile "PJ_DATE" today_time)
    (set_tile "PJ_SXZ" "")
    (set_tile "PJ_DWGNUM" "0")
    (set_tile "PJ_NAME" "工程名称")
    (set_tile "PJ_JZW" "建筑物")
    (action_tile "DHK_CK_CXFILEOUT" "(DHK_CKCXFILEOUT)")
   ; (action_tile "DHK_CK_NEWSXFILEOUT" "(DHK_CKNEWSXFILEOUT)")
    (action_tile "DHK_CK_DWGINSERT" "(setq PJ-sxz  (get_tile \"PJ_SXZ\")) (done_dialog 1) (unload_dialog dcl_EAAD)")
   ; (action_tile "DHK_CK_SXFILEIN" "(DHK_CKSXFILEIN)")
    (action_tile "DHK_CK_CXSXFILEIN" "(DHK_CKCXSXFILEIN)")
    (action_tile "DHK_PJ_REFKILL" "(DHK_PJREFKILL)")
    (action_tile "cancel" "(done_dialog 0)  (unload_dialog dcl_EAAD)")
    (setq dd (start_dialog))
    (if (= dd 1) (DHK_CKDWGINSERT))
)



;|*****************************************************************************
工程设计OA图框DCL对话框功能子程序:初选文件的导出
20200407
--引用全局变量 MEAAD_AZML_V31
|;
;;*****************************************************************************
(defun DHK_CKCXFILEOUT(/ OA_osm ss dwgsum  dwgsum1 dwgsum2 PJNAME PJJZW PJSJR 
PJDATE PJfielname PJXX_file file1 dwgsum_sslen i en mns_ecth)
   (if (= MEAAD_AZML_V31 nil) 
            (progn  (alert "软件安装位置全局变量MEAAD_AZML_V31没有定义!") (exit)))
   (setq OA_osm (getvar "OSMODE"))
   (setvar "OSMODE" 0)
   (setq ss1 (ssget "X" '((0 . "INSERT") (2 . "KYN_*"))))
   (if (/=  ss1 nil)
     (setq dwgsum1 (SORT-SE SS1 2  NIL NIL NIL))
   )
   (setq ss2 (ssget  "X" '((0 . "INSERT") (2 . "AC_*,MCC_*,MNS_*"))))
   (if (/=  ss2 nil)
      (setq dwgsum2 (SORT-SE SS2 2  NIL NIL NIL))
   )
   (cond ((and (/= ss1 nil) (/= nil ss2)) (setq dwgsum (sj2ydq_ssand dwgsum2 dwgsum1)))
         ((and (= ss1 nil) (/= nil ss2)) (setq dwgsum dwgsum2))
         ((and (= ss2 nil) (/= nil ss1)) (setq dwgsum dwgsum1))
         (t (exit))    
   )
   (setq PJNAME "")
   (setq PJJZW "")
   (setq PJSJR "")
   (setq PJname  (get_tile "PJ_NAME"))
   (setq PJJZW (get_tile "PJ_JZW"))
   (setq PJSJR (get_tile "PJ_SJR"))
   (setq PJDATE (get_tile "PJ_DATE"))
   (setq PJfielname (strcat PJname "_" PJJZW "_初选_" PJSJR "_" PJDATE))
   (setq PJXX_file (getfiled "输出 二次参考图初选结果 文件" (strcat MEAAD_AZML_V31 "工程信息3.0\\" PJfielname) "ref" 1))
   (setq file1 (open PJXX_file "w"))
   (setq dwgsum_sslen (sslength dwgsum))
   (setq i 0)
   (setq dwgsum_sslen (sslength dwgsum))
   (setq mns_ecth "")
   (while  (< i dwgsum_sslen) 
         (setq en (ssname dwgsum i)) 
	 (setq uu (entnext en))
	 (setq uu (entget uu))
	 (setq uu (cdr (assoc 0 uu)))
         (if (= uu "ATTRIB") (progn
             (setq mns_ecth (OAGET_ONEatt en "二次图号")) 
             (if  (/= mns_ecth nil) (write-line mns_ecth file1))
         ))
         (setq mns_ecth "") 
         (setq i (+ 1 i))
    )  
   (close file1)
   (setvar "OSMODE" OA_osm)
)


;|*****************************************************************************
工程设计OA图框DCL对话框功能子程序:中间筛选文件的导入
20200407
--引用全局变量 MEAAD_AZML_V31
|;
;;*****************************************************************************
(defun DHK_CKSXFILEIN(/ PJXX_file file1 PJ-name PJ-ectsum ect_num)
   (if (= MEAAD_AZML_V31 nil) 
            (progn  (alert "软件安装位置全局变量MEAAD_AZML_V31没有定义!") (exit)))
   (setq PJXX_file (getfiled "导入 二次参考图中间筛选结果 文件" (strcat MEAAD_AZML_V31 "工程信息3.0\\PJfielname") "ref" 2))
   (setq file1 (open PJXX_file "r"))
   (setq PJ-name (read-line file1))
   (setq PJ-ectsum "")
   (setq ect_num 0)
   (while (/= (setq PJ-ect (read-line file1)) nil) 
        (setq ect_num (+ 1 ect_num))
        (if (/= PJ-ectsum "") 
	      (setq PJ-ectsum (strcat PJ-ectsum ";" PJ-ect))
	      (setq PJ-ectsum  PJ-ect)
        )
   )
   (close file1)
   (set_tile "PJ_NAME" PJ-name)
   (set_tile "PJ_SXZ" (strcat PJ-ectsum ";")) 
   (set_tile "PJ_DWGNUM" (itoa ect_num))
) 



;|*****************************************************************************
工程设计OA图框DCL对话框功能子程序:删除筛选初选ref
20200407
--引用全局变量 MEAAD_AZML_V31
|;
;;*****************************************************************************
(defun DHK_PJREFKILL(/ i delfiles)
        (setq delfiles (vl-directory-files (strcat MEAAD_AZML_V31 "工程信息3.0") "*.ref" 1))
        (if (/= delfiles nil)　(progn
           (setq i 0)
           (while (/= (setq en (nth i delfiles)) nil)
               (setq en (strcat MEAAD_AZML_V31 "工程信息3.0\\" en))
               (vl-file-delete en)
               (setq i (+ i 1))
            )
         ))
)

;|*****************************************************************************
工程设计OA图框DCL对话框功能子程序:初选文件导入，并比对中间筛选结果进行筛选
20200407
--引用全局变量 MEAAD_AZML_V31
|;
;;*****************************************************************************
(defun DHK_CKCXSXFILEIN(/ PJ-sxz PJ-DWGNUM PJXX_file file1 new-ect)
   (if (= MEAAD_AZML_V31 nil) 
            (progn  (alert "软件安装位置全局变量MEAAD_AZML_V31没有定义!") (exit)))
   (setq PJ-sxz  (get_tile "PJ_SXZ"))
   (setq PJ-DWGNUM  (atoi (get_tile "PJ_DWGNUM")))
   (setq PJXX_file (getfiled "导入 需要筛选的初选结果 文件" (strcat MEAAD_AZML_V31 "工程信息3.0\\PJfielname") "ref" 2))
   (setq file1 (open PJXX_file "r"))
   (while (/= (setq new-ect (read-line file1)) nil) 
          (setq new-ect (strcat new-ect ";"))
          (if (= nil (vl-string-search new-ect PJ-sxz)) (setq PJ-sxz (strcat PJ-sxz new-ect)  PJ-DWGNUM (1+ PJ-DWGNUM)))
    )
   (close file1)
   (set_tile "PJ_SXZ" PJ-sxz)
   (set_tile "PJ_DWGNUM" (itoa PJ-DWGNUM))
) 


;|*****************************************************************************
工程设计OA图框DCL对话框功能子程序:最新筛选结果文件导出
20200407
--引用全局变量 MEAAD_AZML_V31
|;
;;*****************************************************************************
(defun DHK_CKNEWSXFILEOUT(/ OA_osm ss dwgsum  dwgsum1 dwgsum2 PJNAME PJJZW PJSJR PJDATE PJfielname PJXX_file file1 dwgsum_sslen i en mns_ecth)
   (if (= MEAAD_AZML_V31 nil) 
            (progn  (alert "软件安装位置全局变量MEAAD_AZML_V31没有定义!") (exit)))
   (setq OA_osm (getvar "OSMODE"))
   (setvar "OSMODE" 0)
   (setq PJ-sxz  (get_tile "PJ_SXZ"))
   (setq PJ-sxz (substr PJ-sxz 1 (- (strlen PJ-sxz) 1)))
   (setq PJ-sxz (parse7 PJ-sxz ";"))
   (setq PJname  (get_tile "PJ_NAME"))
   (setq PJDATE (get_tile "PJ_DATE"))
   (setq PJfielname (strcat PJname "_筛选_" PJDATE))
   (setq PJXX_file (getfiled "输出 二次参考图最新筛选结果 文件" (strcat MEAAD_AZML_V31 "工程信息3.0\\" PJfielname) "ref" 1))
   (setq file1 (open PJXX_file "w"))
   (write-line PJname file1)
   (setq i 0)
   (while  (/= (setq mns_ecth (nth i PJ-sxz)) nil)
         (write-line mns_ecth file1)
         (setq i (+ 1 i))
    )  
   (close file1)
   (setvar "OSMODE" OA_osm)
)



;|*****************************************************************************
工程设计OA图框DCL对话框功能子程序:根据最后的筛选结果文件插入二次参考图
20200407
--引用全局变量 MEAAD_AZML_V31
               Meaad_all_scale
|;
;;*****************************************************************************
(defun DHK_CKDWGINSERT(/ OA_osm PJXX_file pp file1 PJ-ect noprint filenamelist)
   (if (= MEAAD_AZML_V31 nil) 
            (progn  (alert "软件安装位置全局变量MEAAD_AZML_V31没有定义!") (exit)))
   (setq OA_osm (getvar "OSMODE"))
   (setvar "OSMODE" 0)
   (command "-purge" "B" "" "N")
   (setq filenamelist (vl-directory-files (strcat MEAAD_AZML_V31  "二次参考图3.0") "*.dwg" 1))
   (setq noprint "\n二次图库中没有以下二次图：")
      (if  (= Meaad_all_scale nil) (setq meaad_all_scale (getint "\n出图比例因数Meaad_all_scale还没有定义，请输入1：<1,100,200,1000>：")))
      (if  (= Meaad_all_scale nil) (setq meaad_all_scale 1))
   (setq pp (getpoint "\n拾取插入起始点："))
   (setq PJ-sxz (parse7 PJ-sxz ";"))
   (setq i 0)

   (while  (/= (setq PJ-ect (nth i PJ-sxz)) nil)
   (if (/= (vl-position (strcat PJ-ect ".dwg") filenamelist) nil)
               (progn 
                    (command "insert" PJ-ect  pp Meaad_all_scale Meaad_all_scale 0)
                    (command "explode" "L")
                    (setq pp (polar pp (dtr 270) (* Meaad_all_scale 520)))
               )
               (setq noprint (strcat noprint PJ-ect " ; "))
            )
           (setq i (+ 1 i))
    )  
   (command "insert" "DK-ACSM" pp Meaad_all_scale Meaad_all_scale 0)
   (command "explode" "L")
   (setq pp (polar pp (dtr 270) (* Meaad_all_scale 520)))
   (command "insert" "DK-ACIO"  pp Meaad_all_scale Meaad_all_scale 0)
   (command "explode" "L")
   (setvar "OSMODE" OA_osm)
   (if (> (strlen noprint) 30) (alert noprint))
) 


;|*****************************************************************************
工程设计OA图框DCL对话框功能子程序:OA工程图框置换OA标准底框
20200408
|;
;;*****************************************************************************
(defun DHK_OAGCTKZH(/ OA_osm cztk newTK oldppp tddk kd  vn0 tddk_name tddk_sum tddk_sslen 
snn dkdel_sum tp1 Newppp newdwgname newdwgnum gcname zixiang shejihao sjjd banben zhuanye riqi
tp0 mBTK_name v1 v2 p3 vn0 oldname olddwgnum newtkname Zxmfzr1 Zxmfzr2 tkname)

   (setq OA_osm (getvar "OSMODE"))
   (setvar "OSMODE" 0)
   (if  (= Meaad_all_scale nil) (setq meaad_all_scale (getint "\n出图比例因数Meaad_all_scale还没有定义，请输入1：<1,100,200,1000>：")))
    (if  (= Meaad_all_scale nil) (setq meaad_all_scale 1))
   (setq kd (getint "\n置换类别： 1-整块替换 2-属性传递 3-智能替换<3>:"))
   (if (= kd nil) (setq kd 3))
   (cond ((= kd 1)
      (while (/= (setq cztk  (car (entsel  "\n选取OA生成的工程图框作为替代图框："))) nil)
        (setq newTK (ssadd))
        (setq newtk (ssadd cztk newtk)) ;要拷贝的标准图框选择集
        (setq oldppp (OAGET_BLKPOINT cztk));标准图框块插入点
        (princ "\n选择被替换的底框样品：")
        (setq tddk  (car (entsel)))
        (setq vn0 (vlax-ename->vla-object tddk))
        (setq tddk_name (vlax-get-property vn0 "Name"))
        (princ "\n选择被替换的范围：")
        (setq tddk_sum (ssget  '((0 . "insert") (2 . "*图框*_A*框*"))))
        (setq tddk_sslen (sslength tddk_sum))
        (setq snn 0)
        (setq dkdel_sum (ssadd))
        (while (< snn tddk_sslen) 
                 (setq tp1 (ssname tddk_sum snn))
                 (if (= (cdr (assoc 2 (entget tp1))) tddk_name) 
                       (Progn
                              (setq dkdel_sum (ssadd tp1 dkdel_sum))
                              (setq Newppp (OAGET_blkpoint tp1))
                              (setq newdwgname (OAGET_oneatt tp1 "图名"))
                              (setq newdwgnum (OAGET_oneatt tp1 "图号"))
                              (command "copy" newtk "" oldppp newppp)
                              (OAPUT_oneatt (entlast) "图名" newdwgname)
                              (OAPUT_oneatt (entlast) "图号" newdwgnum)
                        )
                  )
                  (setq snn (+ 1 snn))
        )
       (command "erase" dkdel_sum "")
      ))
     ((= kd 2)
         (setq tp1  (car (entsel  "\n选取OA生成的工程图框作为属性提取图框：")))
         (princ "\n选择被替换的范围：")
         (setq tddk (ssget  '((0 . "insert") (2 . "*图框*_A*框*"))))
         (setq tp0 (vlax-ename->vla-object tp1))
         (setq TKname (VLA-get-Name tp0))
         (setq gcname (OAGET_oneatt tp1 "工程名称"))
         (setq zixiang (OAGET_oneatt tp1 "子项"))
         (setq shejihao (OAGET_oneatt tp1 "设计号"))
         (setq sjjd (OAGET_oneatt tp1 "设计阶段"))
         (setq banben (OAGET_oneatt tp1 "版本"))
         (setq zhuanye (OAGET_oneatt tp1 "专业"))
         (setq riqi (OAGET_oneatt tp1 "日期"))
         (setq shengding (OAGET_oneatt tp1 "审定"))
         (setq shenghe (OAGET_oneatt tp1 "审核"))
         (setq xmfzr (OAGET_oneatt tp1 "项目负责人"))
         (setq zyfzr (OAGET_oneatt tp1 "专业负责人"))
         (setq xiaohe (OAGET_oneatt tp1 "校核"))
         (setq sheji (OAGET_oneatt tp1 "设计"))
         (if (wcmatch tkname "*大项目*") 
                      (PROGN
                      (setq Zxmfzr1 (OAGET_oneatt tp1 "项目总负责人1"))
                      (setq Zxmfzr2 (OAGET_oneatt tp1 "项目总负责人2"))
                      )
         )
         (setq tddk_sslen (sslength tddk))
         (setq i 0)
         (while (< i tddk_sslen)  
               (setq en0 (ssname tddk i))
               (setq vn0 (vlax-ename->vla-object en0))
               (setq tddk_name (vlax-get-property vn0 "Name"))
               (if (not (wcmatch tddk_name "*空*"))
                   (progn
                     (OAPUT_ONEATT en0 "工程名称" gcname)  
                     (OAPUT_ONEATT en0 "子项" zixiang) 
                     (OAPUT_ONEATT en0 "设计号" shejihao) 
                     (OAPUT_ONEATT en0 "设计阶段" sjjd) 
                     (OAPUT_ONEATT en0 "版本" banben) 
                     (OAPUT_ONEATT en0 "专业" zhuanye) 
                     (OAPUT_ONEATT en0 "日期" riqi) 
                     (OAPUT_ONEATT en0 "审定" shengding) 
                     (OAPUT_ONEATT en0 "审核" shenghe) 
                     (OAPUT_ONEATT en0 "项目负责人" xmfzr) 
                     (OAPUT_ONEATT en0 "专业负责人" zyfzr) 
                     (OAPUT_ONEATT en0 "校核" xiaohe) 
                     (OAPUT_ONEATT en0 "设计" sheji) 
                     (if (and (wcmatch tkname "*大项目*") (wcmatch tddk_name "*大项目*"))
                        (PROGN
                           (OAput_oneatt en0 "项目总负责人1"  Zxmfzr1)
                           (OAput_oneatt en0 "项目总负责人2"  Zxmfzr2)
                        )
                     )
                   )
               )  
               (setq i (+ 1 i))
         )
     )
     ((= kd 3)
         (setq tp1  (car (entsel  "\n选取OA生成的工程图框作为属性提取图框：")))  
         (princ "\n选择被替换的范围：")
         (setq tddk (ssget  '((0 . "insert") (2 . "*图框*_A*框*"))))
         (setq gcname (OAGET_oneatt tp1 "工程名称"))
         (setq zixiang (OAGET_oneatt tp1 "子项"))
         (setq shejihao (OAGET_oneatt tp1 "设计号"))
         (setq sjjd (OAGET_oneatt tp1 "设计阶段"))
         (setq banben (OAGET_oneatt tp1 "版本"))
         (setq zhuanye (OAGET_oneatt tp1 "专业"))
         (setq riqi (OAGET_oneatt tp1 "日期"))
         (setq shengding (OAGET_oneatt tp1 "审定"))
         (setq shenghe (OAGET_oneatt tp1 "审核"))
         (setq xmfzr (OAGET_oneatt tp1 "项目负责人"))
         (setq zyfzr (OAGET_oneatt tp1 "专业负责人"))
         (setq xiaohe (OAGET_oneatt tp1 "校核"))
         (setq sheji (OAGET_oneatt tp1 "设计"))



         (setq tp0 (vlax-ename->vla-object tp1))
         (setq mBTK_name (vlax-get-property tp0 "Name"))
         (setq v1 (vl-string-search "大项目" mBTK_name))
         (setq v2 (vl-string-search "市政标准" mBTK_name))
         (if (/= v1 nil) 
                      (PROGN
                         (setq Zxmfzr1 (OAGET_oneatt tp1 "项目总负责人1"))
                         (setq Zxmfzr2 (OAGET_oneatt tp1 "项目总负责人2"))
                      )
         )
         (setq tddk_sslen (sslength tddk))
         (setq i 0)
         (while (< i tddk_sslen)  
               (setq en0 (ssname tddk i))
               (setq vn0 (vlax-ename->vla-object en0))
               (setq tddk_name (vlax-get-property vn0 "Name"))
               (setq vv1 (vl-string-search "大项目" tddk_name))
               (setq vv2 (vl-string-search "市政标准" tddk_name))
               (setq p3 (OAGET_BLKPOINT en0))
               (setq oldname (OAGET_ONEatt en0 "图名"))
               (setq olddwgnum (OAGET_ONEatt en0 "图号"))
               (if (not (wcmatch tddk_name "*空*"))
                   (progn 
                          (cond ((and (/= v1 nil) (/= vv1 nil)) ;原大项目目标大项目
                                        (setq newtkname (strcat "OA" (substr tddk_name 5 (- vv1 4)) "大项目")))
                                ((and (/= v1 nil) (/= vv2 nil)) ;原大项目目标标准
                                        (setq newtkname (strcat "OA" (substr tddk_name 5 (- vv2 4)) "大项目")))
                                ((and (/= v2 nil) (/= vv1 nil)) 
                                         (setq newtkname (strcat "OA" (substr tddk_name 5 (- vv1 4)) "标准")))
                                ((and (/= v2 nil) (/= vv2 nil)) 
                                         (setq newtkname (strcat "OA" (substr tddk_name 5 (- vv2 4)) "标准")))                           )
                          (command "erase" en0 "")
                          (command "insert" newtkname p3 Meaad_all_scale Meaad_all_scale 0 "" "" "explode" "L")
                          (setq en0 (entlast))
                          (OAPUT_ONEATT en0 "工程名称" gcname)  
                          (OAPUT_ONEATT en0 "子项" zixiang) 
                          (OAPUT_ONEATT en0 "设计号" shejihao) 
                          (OAPUT_ONEATT en0 "设计阶段" sjjd) 
                          (OAPUT_ONEATT en0 "版本" banben) 
                          (OAPUT_ONEATT en0 "专业" zhuanye) 
                          (OAPUT_ONEATT en0 "日期" riqi) 
                          (OAPUT_ONEATT en0 "图名" oldname) 
                          (OAPUT_ONEATT en0 "图号" olddwgnum) 
                          (OAPUT_ONEATT en0 "审定" shengding) 
                          (OAPUT_ONEATT en0 "审核" shenghe) 
                          (OAPUT_ONEATT en0 "项目负责人" xmfzr) 
                          (OAPUT_ONEATT en0 "专业负责人" zyfzr) 
                          (OAPUT_ONEATT en0 "校核" xiaohe) 
                          (OAPUT_ONEATT en0 "设计" sheji) 
                          (if (/= v1 nil) 
                                    (PROGN
                                         (OAput_oneatt en0 "项目总负责人1"  Zxmfzr1)
                                         (OAput_oneatt en0 "项目总负责人2"  Zxmfzr2)
                                    )
                          )
                   )
               )  
               (setq i (+ 1 i))
         )
     )
   )
   (setvar "OSMODE" OA_osm)
) 




;|*****************************************************************************
工程设计OA图框DCL对话框功能子程序:图框图号编排助手，分手动和自动
20200408
--引用全局变量   Meaad_all_scale  MEAAD_AZML_V31 
|;
;;*****************************************************************************
(DEFUN DHK_OATHBHZS(/ OA_osm b1 b2 b3 b4 b5 b6 stnum bhkind num_st dwgnum_st ss sslen dwgname dwgname1 dwgname2 i i2 i1 
en0 en1 en2 newdwgnum ss_same samelen stwz)
    (if  (= Meaad_all_scale nil) (setq meaad_all_scale (getint "\n出图比例因数Meaad_all_scale还没有定义，请输入1：<1,100,200,1000>：")))
    (if  (= Meaad_all_scale nil) (setq meaad_all_scale 1))
    (setq OA_osm (getvar "OSMODE"))
    (setvar "OSMODE" 0)
    (setq b1  "图号编排工具的适用范围：")
    (setq b2  "\n   （1）图框为标准OA图框或OA底框；")
    (setq b3  "\n   （2）图框排列整齐，每行为下边基本对齐，允许一定误差；")
    (setq b4  "\n   （3）手动编排的首个图框的图名必须正确；")
    (setq b5  "\n   （4）自动编排的图框必须确保图框按顺序排列，从左到右，从上到下；")
    (setq b6  "\n        属于同一图号的图框的图名必须一致；")
    (alert (strcat b1 b2 b3 b4 b5 b6))
    (setq stnum (getstring "\n输入标准起始图号<如SDQ0501-068,CDQ02-001>:"))
    (setq bhkind (getint "\n图纸图号编排类型  1-手动  2-自动<1>："))
    (if (= nil bhkind)  (setq bhkind 1))
    (setq stwz (vl-string-search "-" stnum))
    (setq num_st (atoi (substr stnum (+ 2 stwz) 3)))
    (setq dwgnum_st (substr stnum 1 (+ 1 stwz)))
    (cond ((= bhkind 1)
               (print (strcat "\n选择单张编号为"  (dhk_th33 num_st) "的图框范围："))
               (while  (setq ss (ssget  '((0 . "insert") (2 . "*图框*_A*框*"))))
                       (setq ss (SORT-SE (SORT-SE ss 10 0 (* 150 Meaad_all_scale) nil) 10 1 (* 150 Meaad_all_scale) T))
                       (setq sslen (sslength ss))
                       (setq dwgname (OAget_oneatt (ssname ss 0) "图名"))
                       (setq i 0)
                       (repeat sslen
                            (setq en0 (ssname ss i))
                            (if (=  sslen 1)
                                   (setq newdwgnum (strcat dwgnum_st (DHK_TH33 num_st)))            
                                   (setq newdwgnum (strcat dwgnum_st (DHK_TH33 num_st) "-" (dhk_th22 (+ 1 i)) "/" (dhk_th22 sslen)))
                             )
                            (OAPUT_oneatt en0 "图号"  newdwgnum)
                            (OAPUT_oneatt en0 "图名"  dwgname)
                            (setq i (+ 1 i))
                       )
                       (setq num_st (+ 1 num_st))
                       (print (strcat "\n选择下张编号为" (dhk_th33 num_st) "的图框范围："))
                 )
          ) 
          ((= bhkind 2)
               (print (strcat "\n选择图号自动编号的图框范围："))
               (setq ss (ssget  '((0 . "insert") (2 . "*图框*_A*框*"))))
               (setq ss (SORT-SE (SORT-SE ss 10 0 (* 150 Meaad_all_scale) nil) 10 1 (* 150 Meaad_all_scale) T))
               (setq sslen (sslength ss))
               (setq ss_same (ssadd))
               (setq ss_same (ssadd (ssname ss 0) ss_same))
               (setq i 0)
               (while (< i sslen)
                    (setq en1 (ssname ss i))
                    (setq dwgname1 (OAget_oneatt en1 "图名"))
                    (if (< (+ 1 i) sslen)
                       (progn
                           (setq en2 (ssname ss (+ i 1)))
                           (setq dwgname2 (OAget_oneatt en2 "图名"))
                        )
                       (setq dwgname2 "")
                     )
                     (if (= dwgname1 dwgname2)
                                (progn  (setq ss_same (ssadd en2 ss_same))
                                 )
                                (progn  (setq samelen (sslength ss_same))
                                    (setq i1 0)
                                    (setq i2 0)
                                    (repeat samelen
                                        (setq en0 (ssname ss_same i1))
                                        (if (=  samelen 1)
                                              (setq newdwgnum (strcat dwgnum_st (DHK_TH33 num_st)))            
                                              (setq newdwgnum (strcat dwgnum_st (DHK_TH33 num_st) "-" (dhk_th22 (+ 1 i2)) "/" (dhk_th22 samelen)))
                                         )
                                        (OAPUT_oneatt en0 "图号"  newdwgnum)
                                        (setq i1 (+ i1 1))
                                        (setq i2 (+ 1 i2))
                                     )
                                     (setq num_st (+ 1 num_st))
                                     (setq ss_same (ssadd))
                                     (setq ss_same (ssadd en2 ss_same))
                                )
                     )
                     (setq i (+ 1 i))
               )    
          )
     )
    (setvar "OSMODE" OA_osm)
) 

;|*****************************************************************************
工程设计OA图框DCL对话框功能子程序:OA工程图框图号增减调整
20200409
|;
;;*****************************************************************************
(defun DHK_OATHZJTZ(/ OA_osm tddk_sum tddk_sslen snn n1 tp1 oldwgnum num_st dwgnum_st newdwgnum)
        (setq OA_osm (getvar "OSMODE"))
        (setvar "OSMODE" 0)
        (princ "\n选择图号需调整的图框范围：")
        (setq tddk_sum (ssget  '((0 . "insert") (2 . "*图框*_A*框*"))))
        (setq tddk_sslen (sslength tddk_sum))
        (setq snn 0)
        (setq n1 (getint "\n图纸图号调整值（正值表增加，负值表减少）："))
        (while (< snn tddk_sslen) 
                 (setq tp1 (ssname tddk_sum snn))
                 (setq oldwgnum (OAGET_oneatt  tp1 "图号"))
                 (setq num_st (atoi (substr oldwgnum 9 3)))
                 (setq dwgnum_st (substr oldwgnum 1 8))
                 (setq num_st (+ n1 num_st))
                 (setq newdwgnum (strcat dwgnum_st (DHK_TH33 num_st) (substr oldwgnum 12)))
                 (OAPUT_oneatt tp1 "图号" newdwgnum)
                 (setq snn (+ 1 snn))
        )
       (setvar "OSMODE" OA_osm)
) 


;|*****************************************************************************
工程设计:OA图框编辑器DCL相应主程序
--引用全局变量   Meaad_all_scale  
20200409
|;
;;*****************************************************************************
(DEFUN DHK_OATKBJQ (/ OA_osm  en1  eee  tk_name  tk_num  tk_ver  TK_gcmgkb  TK_gcmzg  TK_gkb  TK_TMgkb  TK_zhuanye  TK_date 
TK_shending  TK_shenhe  TK_XMZFZR1  TK_XMZFZR2  TK_XMFZR  TK_XMFZRGKB  TK_ZYFZR  TK_ZYFZRGKB  TK_xiaohe  TK_sheji 
ss  ss_len  tk snn  dcl_EAAD  dd)
        (setq OA_osm (getvar "OSMODE"))
        (setvar "OSMODE" 0)
        (princ "\n选择含原信息的OA图框：")
        (setq en1 (car (entsel)))
        (setq eee (entget en1))
        (setq meaad_all_scale (cdr (assoc 41 eee)))
        (setq tk_name (OAGET_oneatt en1 "图名"))
        (setq tk_num (OAGET_oneatt en1 "图号"))
        (setq tk_ver (OAGET_oneatt en1 "版本"))
        (setq TK_gcmgkb (OAget_ONEATT_ZBV en1 "工程名称" 41))
        (setq TK_gcmzg (OAget_ONEATT_ZBV en1 "工程名称" 40))
        (setq TK_gkb (OAget_ONEATT_ZBV en1 "图号" 41))
        (setq TK_TMgkb (OAget_ONEATT_ZBV en1 "图名" 41))
        (setq TK_TMzg (OAget_ONEATT_ZBV en1 "图名" 40))
        (setq TK_zhuanye (OAget_ONEATT en1 "专业"))
        (setq TK_date (OAget_ONEATT en1 "日期"))
        (setq TK_shending (OAget_ONEATT en1 "审定"))
        (setq TK_shenhe (OAget_ONEATT en1 "审核"))
        (setq TK_XMZFZR1 (OAget_ONEATT en1 "项目总负责人1"))
        (setq TK_XMZFZR2 (OAget_ONEATT en1 "项目总负责人2"))
        (setq TK_XMFZR (OAget_ONEATT en1 "项目负责人"))
        (setq TK_XMFZRGKB (OAget_ONEATT_ZBV en1 "项目负责人" 41))
        (setq TK_ZYFZR (OAget_ONEATT en1 "专业负责人"))
        (setq TK_ZYFZRGKB (OAget_ONEATT_ZBV en1 "专业负责人" 41))
        (setq TK_xiaohe (OAget_ONEATT en1 "校核"))
        (setq TK_sheji (OAget_ONEATT en1 "设计"))
        (princ "\n选择要编辑的图框范围：")
        (setq ss (ssget  '((0 . "insert") (2 . "*图框*_A*框*"))))
        (while (/= ss nil)
           (setq ss (SORT-SE (SORT-SE ss 10 0 (* 150 Meaad_all_scale) nil) 10 1 (* 150 Meaad_all_scale) T))
           (setq ss_len (sslength ss))
           (setq tk (ssname ss 0))
           (setq snn 0)
           (setq dcl_EAAD (load_dialog "Meaad_OATK_3.0.dcl"))
           (if (not  (new_dialog "MEAAD3_OA_TKBJQ" dcl_EAAD))  (exit))
           (set_tile "PJXX_NAME" "1")
           (set_tile "PJXX_NUM" "1")
           (set_tile "PJXX_VER" "0")
           (set_tile "PJXX_HOUZHUI" "0")
           (set_tile "PJXX_GKB" "0")
           (set_tile "PJ_NAME" tk_name)
           (set_tile "PJ_NUM" tk_num)
           (set_tile "PJXX_TMGKB" "0")
           (set_tile "PJXX_GCMGKB" "0")
           (set_tile "PJXX_TMZG" "0")
           (set_tile "PJXX_GCMZGB" "0")
           (set_tile "PJXX_ZHUANYE" "0")
           (set_tile "PJXX_DATE" "0")
           (set_tile "PJXX_SHENDING" "0")
           (set_tile "PJXX_SHENHE" "0")
           (set_tile "PJXX_XMZFZR1" "0")
           (set_tile "PJXX_XMZFZR2" "0")
           (set_tile "PJXX_XMFZR" "0")
           (set_tile "PJXX_XMFZRGKB" "0")
           (set_tile "PJXX_ZYFZR" "0")
           (set_tile "PJXX_ZYFZRGKB" "0")
           (set_tile "PJXX_XIAOHE" "0")
           (set_tile "PJXX_SHEJI" "0")
           (if (/= tk_ver nil) 
               (set_tile "PJ_VER" tk_ver)
               (set_tile "PJ_VER" "")
           )
          (set_tile "PJ_GKB" (rtos TK_gkb 2 2))
          (set_tile "PJ_HOUZHUI" "")
          (set_tile "PJ_TMGKB" (rtos TK_tmgkb 2 2))
          (set_tile "PJ_GCMGKB" (rtos TK_gcmgkb 2 2))
          (set_tile "PJ_TMZG" (rtos TK_tmzg 2 2))
          (set_tile "PJ_GCMZG" (rtos TK_gcmzg 2 2))
          (set_tile "PJ_ZHUANYE" TK_zhuanye)
          (set_tile "PJ_DATE" TK_date)
          (set_tile "PJ_SHENDING" TK_shending)
          (set_tile "PJ_SHENHE" TK_shenhe)
          (if (/= TK_XMZFZR1 nil) (set_tile "PJ_XMZFZR1" TK_XMZFZR1))
          (if (/= TK_XMZFZR2 nil) (set_tile "PJ_XMZFZR2" TK_XMZFZR2))
          (set_tile "PJ_XMFZR" TK_XMFZR)
          (set_tile "PJ_XMFZRGKB" (rtos TK_XMFZRGKB 2 2))
          (set_tile "PJ_ZYFZR" TK_ZYFZR)
          (set_tile "PJ_ZYFZRGKB" (rtos TK_ZYFZRGKB 2 2))
          (set_tile "PJ_XIAOHE" TK_xiaohe)
          (set_tile "PJ_SHEJI" TK_sheji)
          (action_tile "DHK_BJ_SZTZXG" "(DHK_BJSZTZXG) (done_dialog 1)  (unload_dialog dcl_EAAD)")
          (action_tile "DHK_BJ_XMQML" "(DHK_BJXMQML)")
          (action_tile "DHK_BJ_DXMQML" "(DHK_BJDXMQML)")
          (action_tile "DHK_BJ_QCQMLGX" "(DHK_BJQCQMLGX)") 
          (action_tile "DHK_BJ_QCQML" "(DHK_BJQCQML)")      
          (action_tile "cancel" "(done_dialog 0)  (unload_dialog dcl_EAAD)")
          (setq dd (start_dialog))
          (princ "\n选择含原信息的OA图框：")
          (setq en1 (car (entsel)))
          (if (/= en1 nil) 
              (progn
                 (setq tk_name (OAGET_oneatt en1 "图名"))
                 (setq tk_num (OAGET_oneatt en1 "图号"))
                 (setq tk_ver (OAGET_oneatt en1 "版本"))
                 (setq TK_gcmgkb (OAget_ONEATT_ZBV en1 "工程名称" 41))
                 (setq TK_gcmzg (OAget_ONEATT_ZBV en1 "工程名称" 40))
                 (setq TK_gkb (OAget_ONEATT_ZBV en1 "图号" 41))
                 (setq TK_TMgkb (OAget_ONEATT_ZBV en1 "图名" 41))
                 (setq TK_TMzg (OAget_ONEATT_ZBV en1 "图名" 40))
                 (setq TK_zhuanye (OAget_ONEATT en1 "专业"))
                 (setq TK_date (OAget_ONEATT en1 "日期"))
                 (setq TK_shending (OAget_ONEATT en1 "审定"))
                 (setq TK_shenhe (OAget_ONEATT en1 "审核"))
                 (setq TK_XMZFZR1 (OAget_ONEATT en1 "项目总负责人1"))
                 (setq TK_XMZFZR2 (OAget_ONEATT en1 "项目总负责人2"))
                 (setq TK_XMFZR (OAget_ONEATT en1 "项目负责人"))
                 (setq TK_XMFZRGKB (OAget_ONEATT_ZBV en1 "项目负责人" 41))
                 (setq TK_ZYFZR (OAget_ONEATT en1 "专业负责人"))
                 (setq TK_ZYFZRGKB (OAget_ONEATT_ZBV en1 "专业负责人" 41))
                 (setq TK_xiaohe (OAget_ONEATT en1 "校核"))
                 (setq TK_sheji (OAget_ONEATT en1 "设计"))

                 (princ "\n选择要编辑的图框范围：")
                 (setq ss (ssget  '((0 . "insert") (2 . "*图框*_A*框*"))))
               )
              (setq ss nil)
          )
        )
       (setvar "OSMODE" OA_osm)
) 


;|*****************************************************************************
工程设计OA图框编辑器:单个图框编辑勾选箱快捷方式
20211201
|;
;;*****************************************************************************
(DEFUN DHK_BJXMQML ()
           (set_tile "PJXX_SHENDING" "1")
           (set_tile "PJXX_SHENHE" "1")
           (set_tile "PJXX_XMZFZR1" "0")
           (set_tile "PJXX_XMZFZR2" "0")
           (set_tile "PJXX_XMFZR" "1")
           (set_tile "PJXX_ZYFZR" "1")
           (set_tile "PJXX_XIAOHE" "1")
           (set_tile "PJXX_SHEJI" "1")
)
(DEFUN DHK_BJDXMQML ()
           (set_tile "PJXX_SHENDING" "1")
           (set_tile "PJXX_SHENHE" "1")
           (set_tile "PJXX_XMZFZR1" "1")
           (set_tile "PJXX_XMZFZR2" "1")
           (set_tile "PJXX_XMFZR" "1")
           (set_tile "PJXX_ZYFZR" "1")
           (set_tile "PJXX_XIAOHE" "1")
           (set_tile "PJXX_SHEJI" "1")
)
(DEFUN DHK_BJQCQMLGX ()
           (set_tile "PJXX_SHENDING" "0")
           (set_tile "PJXX_SHENHE" "0")
           (set_tile "PJXX_XMZFZR1" "0")
           (set_tile "PJXX_XMZFZR2" "0")
           (set_tile "PJXX_XMFZR" "0")
           (set_tile "PJXX_ZYFZR" "0")
           (set_tile "PJXX_XIAOHE" "0")
           (set_tile "PJXX_SHEJI" "0")
)

(DEFUN DHK_BJQCQML ()
          (set_tile "PJ_SHENDING" "")
          (set_tile "PJ_SHENHE" "")
          (set_tile "PJ_XMZFZR1" "")
          (set_tile "PJ_XMZFZR2" "")
          (set_tile "PJ_XMFZR" "")
          (set_tile "PJ_XMFZRGKB" "")
          (set_tile "PJ_ZYFZR" "")
          (set_tile "PJ_ZYFZRGKB" "")
          (set_tile "PJ_XIAOHE" "")
          (set_tile "PJ_SHEJI" "")
)


;|*****************************************************************************
工程设计OA图框编辑器:单个图框编辑
20200409
|;
;;*****************************************************************************
(DEFUN DHK_BJSZTZXG (/ xxtm  xxth  xxver  xxhz  xxgkb  xxtmgkb xxgcmgkb  xxtmzg  xxgcmzg  XXZHUANYE  
XXDATE  XXSHENDING XXSHENHE  XXXMZFZR1  XXXMZFZR2  XXXMFZR  XXXMFZRGKB  XXZYFZR  XXZYFZRGKB  XXXIAOHE  
XXSHEJI th tm gkbb tmgkbb gcmgkbb  tmzgb  gcmzgb  verr  hz  ZHUANYE  RIQI  SHENDING  SHENHE  XMZFZR1  
XMZFZR2 XMFZR  XMFZRGKB  ZYFZR  ZYFZRGKB  XIAOHE  SHEJI  stwz  numst  newth n2 newth)
        (setq xxtm (get_tile "PJXX_NAME"))
        (setq xxth (get_tile "PJXX_NUM"))
        (setq xxver (get_tile "PJXX_VER"))
        (setq xxhz (get_tile "PJXX_HOUZHUI"))
        (setq xxgkb (get_tile "PJXX_GKB"))
        (setq xxtmgkb (get_tile "PJXX_TMGKB"))
        (setq xxgcmgkb (get_tile "PJXX_GCMGKB"))
        (setq xxtmzg (get_tile "PJXX_TMZG"))
        (setq xxgcmzg (get_tile "PJXX_GCMZG"))
        (setq XXZHUANYE (get_tile "PJXX_ZHUANYE"))
        (setq XXDATE (get_tile "PJXX_DATE"))
        (setq XXSHENDING (get_tile "PJXX_SHENDING"))
        (setq XXSHENHE (get_tile "PJXX_SHENHE"))
        (setq XXXMZFZR1 (get_tile "PJXX_XMZFZR1"))
        (setq XXXMZFZR2 (get_tile "PJXX_XMZFZR2"))
        (setq XXXMFZR (get_tile "PJXX_XMFZR"))
        (setq XXXMFZRGKB (get_tile "PJXX_XMFZRGKB"))
        (setq XXZYFZR (get_tile "PJXX_ZYFZR"))
        (setq XXZYFZRGKB (get_tile "PJXX_ZYFZRGKB"))
        (setq XXXIAOHE (get_tile "PJXX_XIAOHE"))
        (setq XXSHEJI (get_tile "PJXX_SHEJI"))
        (setq tm (get_tile "PJ_NAME"))
        (setq th (get_tile "PJ_NUM"))
        (setq gkbb (get_tile "PJ_GKB"))
        (setq tmgkbb (get_tile "PJ_TMGKB"))
        (setq gcmgkbb (get_tile "PJ_GCMGKB"))
        (setq tmzgb (get_tile "PJ_TMZG"))
        (setq gcmzgb (get_tile "PJ_GCMZG"))
        (setq verr (get_tile "PJ_VER"))
        (setq hz (get_tile "PJ_HOUZHUI"))
        (setq ZHUANYE (get_tile "PJ_ZHUANYE"))
        (setq RIQI (get_tile "PJ_DATE"))
        (setq SHENDING (get_tile "PJ_SHENDING"))
        (setq SHENHE (get_tile "PJ_SHENHE"))
        (setq XMZFZR1 (get_tile "PJ_XMZFZR1"))
        (setq XMZFZR2 (get_tile "PJ_XMZFZR2"))
        (setq XMFZR (get_tile "PJ_XMFZR"))
        (setq XMFZRGKB (get_tile "PJ_XMFZRGKB"))
        (setq ZYFZR (get_tile "PJ_ZYFZR"))
        (setq ZYFZRGKB (get_tile "PJ_ZYFZRGKB"))
        (setq XIAOHE (get_tile "PJ_XIAOHE"))
        (setq SHEJI (get_tile "PJ_SHEJI"))
        (setq stwz (vl-string-search "-" th))
        (setq numst (substr th 1 (+ 4 stwz)))
        (setq newth (strcat numst "-01/" (dhk_th22 ss_len)))
        (if (= ss_len 1) 
             (progn
                (if (= xxtm "1")  (OAPUT_oneatt tk "图名" tm))
                (if (= xxth "1")  (OAPUT_oneatt tk "图号" numst))
                (if (= xxver "1")  (OAPUT_oneatt tk "版本" verr))
                (if (= xxhz "1")  (progn
                             (setq newth (strcat numst hz))
                             (OAPUT_oneatt tk "图号" newth)
                 ))
                 (if (= xxgkb "1")  (OAPUT_oneatt_ZBV tk "图号" 41 (atof gkbb)))

                 (if (= xxtmgkb "1")  (OAPUT_oneatt_ZBV tk "图名" 41 (atof tmgkbb)))
                 (if (= xxgcmgkb "1")  (OAPUT_oneatt_ZBV tk "工程名称" 41 (atof gcmgkbb)))
                 (if (= xxtmzg "1")  (OAPUT_oneatt_ZBV tk "图名" 40 (atof tmzgb)))
                 (if (= xxgcmzg "1")  (OAPUT_oneatt_ZBV tk "工程名称" 40 (atof gcmzgb)))
                (if (= XXZHUANYE "1")  (OAPUT_oneatt tk "专业" zhuanye))
                (if (= XXDATE "1")  (OAPUT_oneatt tk "日期" riqi))
                (if (= XXSHENDING "1")  (OAPUT_oneatt tk "审定" shending))
                (if (= XXSHENHE "1")  (OAPUT_oneatt tk "审核" shenhe))
                (if (= XXXMZFZR1 "1")  (OAPUT_oneatt tk "项目总负责人1" xmzfzr1))
                (if (= XXXMZFZR2 "1")  (OAPUT_oneatt tk "项目总负责人2" xmzfzr2))
                (if (= XXXMFZR "1")  (OAPUT_oneatt tk "项目负责人" xmfzr))
                (if (= XXZYFZR "1")  (OAPUT_oneatt tk "专业负责人" zyfzr))
                (if (= XXXIAOHE "1")  (OAPUT_oneatt tk "校核" xiaohe))
                (if (= XXSHEJI "1")  (OAPUT_oneatt tk "设计" sheji))
                  (if (= XXXMFZRGKB "1") (progn 
                          (cond ((/= xmFZRGKB "A") (OAPUT_oneatt_ZBV tk "项目负责人" 41 (atof xmFZRGKB)))
                                ((and (= xmFZRGKB "A") (< (Strlen xmFZR) 12)) (OAPUT_oneatt_ZBV tk "项目负责人" 41 0.9))
                                ((and (= xmFZRGKB "A") (>= (Strlen xmFZR) 12)) (OAPUT_oneatt_ZBV tk "项目负责人" 41 0.8))
                          ))
                )

                (if (= XXZYFZRGKB "1") (progn
                          (cond ((/= ZYFZRGKB "A") (OAPUT_oneatt_ZBV tk "专业负责人" 41 (atof ZYFZRGKB)))
                                ((and (= ZYFZRGKB "A") (< (Strlen ZYFZR) 12)) (OAPUT_oneatt_ZBV tk "专业负责人" 41 0.9))
                                ((and (= ZYFZRGKB "A") (>= (Strlen ZYFZR) 12)) (OAPUT_oneatt_ZBV tk "专业负责人" 41 0.8))
                          ))
                )
             )
            (progn
                (setq n2 0)
                (repeat ss_len
                   (setq tk (ssname ss n2))
                   (setq newth (strcat numst "-" (dhk_th22 (+ 1 n2)) "/" (dhk_th22 ss_len)))
                   (if (= xxtm "1")  (OAPUT_oneatt tk "图名" tm))
                   (if (= xxth "1")  (progn
                                         (setq newth (strcat numst "-" (dhk_th22 (+ 1 n2)) "/" (dhk_th22 ss_len)))
                                         (OAPUT_oneatt tk "图号" newth)
                                      )
                                      (progn
                                            (setq th (OAGET_oneatt tk "图号"))
                                            (setq newth th)
                                      )
                   )                                     
                   (if (= xxver "1")  (OAPUT_oneatt tk "版本" verr))
                   (if (= xxhz "1")  (progn
                             (setq newth (strcat newth hz))
                             (cond ((= (strlen newth) 19)  (OAPUT_oneatt_ZBV tk "图号" 41 0.8))
                                   ((>= (strlen newth) 20)  (OAPUT_oneatt_ZBV tk "图号" 41 0.7))
                                   ((<= (strlen newth) 18)  (OAPUT_oneatt_ZBV tk "图号" 41 0.9))
                             )
                             (OAPUT_oneatt tk "图号" newth)
                    ))
                   (if (= xxgkb "1")  
                         (progn 
                             (cond ((/= gkbb "A") (OAPUT_oneatt_ZBV tk "图号" 41 (atof gkbb)))
                                ((and (= gkbb "A") (< (strlen newth) 18)) (OAPUT_oneatt_ZBV tk "图号" 41 0.9))
                                ((and (= gkbb "A") (= (strlen newth) 19)) (OAPUT_oneatt_ZBV tk "图号" 41 0.8))
                                ((and (= gkbb "A") (>= (strlen newth) 20)) (OAPUT_oneatt_ZBV tk "图号" 41 0.75))
                              )
                          )
                  )


                   (if (= xxtmgkb "1")  (OAPUT_oneatt_ZBV tk "图名" 41 (atof tmgkbb)))
                   (if (= xxgcmgkb "1")  (OAPUT_oneatt_ZBV tk "工程名称" 41 (atof gcmgkbb)))
                   (if (= xxtmzg "1")  (OAPUT_oneatt_ZBV tk "图名" 40 (atof tmzgb)))
                   (if (= xxgcmzg "1")  (OAPUT_oneatt_ZBV tk "工程名称" 40 (atof gcmzgb)))
                   (if (= XXZHUANYE "1")  (OAPUT_oneatt tk "专业" zhuanye))
                   (if (= XXDATE "1")  (OAPUT_oneatt tk "日期" riqi))
                   (if (= XXSHENDING "1")  (OAPUT_oneatt tk "审定" shending))
                   (if (= XXSHENHE "1")  (OAPUT_oneatt tk "审核" shenhe))
                   (if (= XXXMZFZR1 "1")  (OAPUT_oneatt tk "项目总负责人1" xmzfzr1))
                   (if (= XXXMZFZR2 "1")  (OAPUT_oneatt tk "项目总负责人2" xmzfzr2))
                   (if (= XXXMFZR "1")  (OAPUT_oneatt tk "项目负责人" xmfzr))
                   (if (= XXZYFZR "1")  (OAPUT_oneatt tk "专业负责人" zyfzr))
                   (if (= XXXIAOHE "1")  (OAPUT_oneatt tk "校核" xiaohe))
                   (if (= XXSHEJI "1")  (OAPUT_oneatt tk "设计" sheji))
                  (if (= XXXMFZRGKB "1")  (progn
                          (cond ((/= xmFZRGKB "A") (OAPUT_oneatt_ZBV tk "项目负责人" 41 (atof xmFZRGKB)))
                                ((and (= xmFZRGKB "A") (< (Strlen xmFZR) 12)) (OAPUT_oneatt_ZBV tk "项目负责人" 41 0.9))
                                ((and (= xmFZRGKB "A") (>= (Strlen xmFZR) 12)) (OAPUT_oneatt_ZBV tk "项目负责人" 41 0.8))
                          ))
                  )

                  (if (= XXZYFZRGKB "1") (progn
                          (cond ((/= ZYFZRGKB "A") (OAPUT_oneatt_ZBV tk "专业负责人" 41 (atof ZYFZRGKB)))
                                ((and (= ZYFZRGKB "A") (< (Strlen ZYFZR) 12)) (OAPUT_oneatt_ZBV tk "专业负责人" 41 0.9))
                                ((and (= ZYFZRGKB "A") (>= (Strlen ZYFZR) 12)) (OAPUT_oneatt_ZBV tk "专业负责人" 41 0.8))
                          ))
                 )
                  (setq n2 (+ 1 n2))
                )
            )
        )
 )


;|*****************************************************************************
工程设计:OA目录编辑器DCL相应主程序 
20200409
|;
;;*****************************************************************************
(DEFUN DHK_OAMLBJQ (/ OA_osm ss ss_len tk tk_name tk_num tk_ver dcl_EAAD)
        (setq OA_osm (getvar "OSMODE"))
        (setvar "OSMODE" 0)
        (princ "\n选择要编辑的目录范围：")
        (setq ss (ssget  '((0 . "insert") (2 . "OA图框_图纸目录单行"))))
        (while (/= ss nil)
           (setq ss_len (sslength ss))
           (setq tk (ssname ss 0))
           (setq snn 0)
           (setq dcl_EAAD (load_dialog "Meaad_OATK_3.0.dcl"))
           (if (not  (new_dialog "MEAAD3_OA_MLBJQ" dcl_EAAD))  (exit))
           (set_tile "PJXX_GKB" "1")
           (set_tile "PJXX_HOUZHUI" "1")
           (set_tile "PJXX_VER" "0")
           (action_tile "DHK_BJ_TZMLXG" "(DHK_BJTZMLXG) (done_dialog 1)  (unload_dialog dcl_EAAD)")
           (action_tile "cancel" "(done_dialog 0)  (unload_dialog dcl_EAAD)")
           (start_dialog)
           (princ "\n选择要编辑的目录范围：")
           (setq ss (ssget  '((0 . "insert") (2 . "OA图框_图纸目录单行"))))
        )
       (setvar "OSMODE" OA_osm)
) 


;|*****************************************************************************
工程设计OA目录编辑器:多个编辑
20200409
|;
;;*****************************************************************************
(DEFUN DHK_BJTZMLXG (/ xxver verr n2 tk tk_num newth xxhz xxgkb gkbb hz) 
        (setq xxver (get_tile "PJXX_VER"))
        (setq xxhz (get_tile "PJXX_HOUZHUI"))
        (setq xxgkb (get_tile "PJXX_GKB"))
        (setq verr (get_tile "PJ_VER"))
        (setq gkbb (get_tile "PJ_GKB"))
        (setq hz (get_tile "PJ_HOUZHUI"))
        (setq n2 0)
        (repeat ss_len
           (setq tk (ssname ss n2))
           (setq tk_num (OAGET_oneatt tk "图纸图号"))
           (setq newth (strcat tk_num hz))
           (if (= xxver "1")  (OAPUT_oneatt tk "图纸版号" verr))
           (if (= xxhz "1") (OAPUT_oneatt tk "图纸图号" newth))
           (if (= xxgkb "1")  (OAPUT_oneatt_ZBV tk "图纸名称" 41 (atof gkbb)))
           (setq n2 (+ 1 n2))
        )
)



;***************************************************************************
;;; OA标准图框工具：图框属性文字纠偏
;;; 全局比例因子 Meaad_all_Scale
;;; 含标准图框和大项目图框
;;;***************************************************************************
(DEFUN DHK_OATKWZGW (/  DQ2y_osm tddk_sum tddk_sslen snn tp1 ttt tkname x y p P11 P12 P21 P22 
                 P31 P32 P41 P42 P43 P51 P52 P53 P61 P62 P63 mst kkk ttt jjj p101 p6310 
                 P6311 P1110 P1111 P1210 P1211 P2110 P2111 P2210 P2211 P3110 P3111 P3210 
                 thnum_len thend P3211 P4110 P4111 P4210 P4211 P4310 P4311 P5110 P5111 
                 P5210 P5211 P5310 P5311 P6110 P6100 P6210 P6211)
    (setq OA_osm (getvar "OSMODE"))
    (setvar "OSMODE" 0)
    (if  (= Meaad_all_scale nil) (setq meaad_all_scale (getint "\n出图比例因数Meaad_all_scale还没有定义，请输入1：<1,100,200,1000>："))) 
    (if  (= Meaad_all_scale nil) (setq meaad_all_scale 1))
    (princ "\n选择需要归位的文字跑偏OA图框：")
    (setq tddk_sum (ssget  '((0 . "insert") (2 . "*图框_A*框*"))))
    (setq thend "")
    (setq tddk_sslen (sslength tddk_sum))
    (setq snn 0)
    (while (< snn tddk_sslen) 
         (setq tp1 (ssname tddk_sum snn))
	 (setq ttt (entget tp1))
         (setq tkname (cdr (assoc 2 ttt))) 
              ;-----------获取图框插入点-------------------------
              (setq x (cadr (assoc 10 ttt)))
              (setq y (caddr (assoc 10 ttt)))
              (setq p (list x y 0.0))
              ;-----------推算定位点----------------------------
              (cond ((wcmatch tkname "标准图框_A0_1189_*框*") (setq x (+ x (* meaad_all_scale 1189))))                         
                    ((wcmatch tkname "标准图框_A0加_1337_*框*") (setq x (+ x (* meaad_all_scale 1337))))
                    ((wcmatch tkname "标准图框_A0加_1486_*框*") (setq x (+ x (* meaad_all_scale 1486))))
                    ((wcmatch tkname "标准图框_A0加_1783_*框*") (setq x (+ x (* meaad_all_scale 1783))))
                    ((wcmatch tkname "标准图框_A0加_2080_*框*") (setq x (+ x (* meaad_all_scale 2080))))
                    ((wcmatch tkname "标准图框_A0加_2378_*框*") (setq x (+ x (* meaad_all_scale 2378))))
                    ((wcmatch tkname "标准图框_A1_841_*框*") (setq x (+ x (* meaad_all_scale 841))))
                    ((wcmatch tkname "标准图框_A1加_946_*框*") (setq x (+ x (* meaad_all_scale 946))))
                    ((wcmatch tkname "标准图框_A1加_1051_*框*") (setq x (+ x (* meaad_all_scale 1051))))
                    ((wcmatch tkname "标准图框_A1加_1261_*框*") (setq x (+ x (* meaad_all_scale 1261))))
                    ((wcmatch tkname "标准图框_A1加_1471_*框*") (setq x (+ x (* meaad_all_scale 1471))))
                    ((wcmatch tkname "标准图框_A1加_1682_*框*") (setq x (+ x (* meaad_all_scale 1682))))
                    ((wcmatch tkname "标准图框_A2_594_*框*") (setq x (+ x (* meaad_all_scale 594))))
                    ((wcmatch tkname "标准图框_A2加_668_*框*") (setq x (+ x (* meaad_all_scale 668))))
                    ((wcmatch tkname "标准图框_A2加_742_*框*") (setq x (+ x (* meaad_all_scale 742))))
                    ((wcmatch tkname "标准图框_A2加_891_*框*") (setq x (+ x (* meaad_all_scale 891))))
                    ((wcmatch tkname "标准图框_A2加_1039_*框*") (setq x (+ x (* meaad_all_scale 1039))))
                    ((wcmatch tkname "标准图框_A2加_1188_*框*") (setq x (+ x (* meaad_all_scale 1188))))
                    ((wcmatch tkname "标准图框_A3_420_*框*") (setq x (+ x (* meaad_all_scale 420))))
                    ((wcmatch tkname "标准图框_A3加_472_*框*") (setq x (+ x (* meaad_all_scale 472))))
                    ((wcmatch tkname "标准图框_A3加_525_*框*") (setq x (+ x (* meaad_all_scale 525))))
                    ((wcmatch tkname "标准图框_A3加_630_*框*") (setq x (+ x (* meaad_all_scale 630))))
                    ((wcmatch tkname "标准图框_A3加_735_*框*") (setq x (+ x (* meaad_all_scale 735))))
                    ((wcmatch tkname "标准图框_A3加_840_*框*") (setq x (+ x (* meaad_all_scale 840))))
              )
              (setq p11 (list (- x (* meaad_all_scale 184.5)) (+ y (* meaad_all_scale 25))))
              (setq p12 (polar p11 0 (* meaad_all_scale 51)))
              (setq p21 (polar p11 (dtr 270) (* meaad_all_scale 6)))
              (setq p31 (polar p21 (dtr 270) (* meaad_all_scale 6)))
              (setq p22 (polar p21 0 (* meaad_all_scale 51)))
              (setq p32 (polar p31 0 (* meaad_all_scale 51)))
              (setq P61 (list (- x (* meaad_all_scale 51.77145)) (+ y (* meaad_all_scale 45))))
              (setq p62 (polar p61 (dtr 270) (* meaad_all_scale 8)))
              (setq p63 (polar p61 (dtr 270) (* meaad_all_scale 17)))
              (setq P41 (list (- x (* meaad_all_scale 80.438)) (+ y (* meaad_all_scale 19))))  
              (setq p42 (polar p41 0 (* meaad_all_scale 35.2331)))   
              (setq p43 (polar p42 0 (* meaad_all_scale 26.8958)))          
              (setq p51 (polar p41 (dtr 270) (* meaad_all_scale 6)))
              (setq p52 (polar p51 0 (* meaad_all_scale 35.2331))) 
              (setq p53 (polar p52 0 (* meaad_all_scale 26.8958)))  
              ;---------------文字归位程序 --------------------------
             (setq mst tp1)
	     (setq kkk (cdr (assoc 0 ttt)))
	     (while (/= kkk "SEQEND")
		    (setq mst (entnext mst))
		    (setq ttt (entget mst))
		    (setq kkk (cdr (assoc 0 ttt)))
		    (setq JJJ (cdr (assoc 2 ttt)))
                    (cond 
                         ((= JJJ "图名") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p6310 (list 10 (car p63) (cadr P63) 0))
                                     (setq p6311 (list 11 (car p63) (cadr P63) 0)) 
                                     (while (/= 11 (car (nth iii ttt)))
                                           (setq iii (+ 1 iii))
                                      )
                                     (setq ttt (subst p6311 (nth iii ttt) ttt))
                                     (setq iii (+ 1 iii))
                                     (while (/= 11 (car (nth iii ttt)))
                                           (setq iii (+ 1 iii))
                                      )
                                     (setq ttt (subst p6311 (nth iii ttt) ttt))
                                     (setq iii (+ 1 iii))
                                     (while (/= 10 (car (nth iii ttt)))
                                           (setq iii (+ 1 iii))
                                      )
                                     (setq ttt (subst p6310 (nth iii ttt) ttt))
                                     (entmod ttt)
                             ))

                        )
                        ((= JJJ "工程名称") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p6110 (list 10 (car p61) (cadr P61) 0))
                                     (setq p6111 (list 11 (car p61) (cadr P61) 0)) 
                                     (while (/= 11 (car (nth iii ttt)))
                                           (setq iii (+ 1 iii))
                                      )
                                     (setq ttt (subst p6111 (nth iii ttt) ttt))
                                     (setq iii (+ 1 iii))
                                     (while (/= 11 (car (nth iii ttt)))
                                           (setq iii (+ 1 iii))
                                      )
                                     (setq ttt (subst p6111 (nth iii ttt) ttt))
                                     (setq iii (+ 1 iii))
                                     (while (/= 10 (car (nth iii ttt)))
                                           (setq iii (+ 1 iii))
                                      )
                                     (setq ttt (subst p6110 (nth iii ttt) ttt))
                                     (entmod ttt)
                             ))

                      )
                        ((= JJJ "子项") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p6210 (list 10 (car p62) (cadr P62) 0))
                                     (setq p6211 (list 11 (car p62) (cadr P62) 0)) 
                                     (while (/= 11 (car (nth iii ttt)))
                                           (setq iii (+ 1 iii))
                                      )
                                     (setq ttt (subst p6211 (nth iii ttt) ttt))
                                     (setq iii (+ 1 iii))
                                     (while (/= 11 (car (nth iii ttt)))
                                           (setq iii (+ 1 iii))
                                      )
                                     (setq ttt (subst p6211 (nth iii ttt) ttt))
                                     (setq iii (+ 1 iii))
                                     (while (/= 10 (car (nth iii ttt)))
                                           (setq iii (+ 1 iii))
                                      )
                                     (setq ttt (subst p6210 (nth iii ttt) ttt))
                                     (entmod ttt)
                             ))

                      )

                        ((= JJJ "图号") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p5110 (list 10 (car p51) (cadr P51) 0))
                                     (setq p5111 (list 11 (car p51) (cadr P51) 0)) 
                                     (while (/= 11 (car (nth iii ttt)))
                                           (setq iii (+ 1 iii))
                                      )
                                     (setq ttt (subst p5111 (nth iii ttt) ttt))
                                     (setq iii (+ 1 iii))
                                     (while (/= 11 (car (nth iii ttt)))
                                           (setq iii (+ 1 iii))
                                      )
                                     (setq ttt (subst p5111 (nth iii ttt) ttt))
                                     (setq iii (+ 1 iii))
                                     (while (/= 10 (car (nth iii ttt)))
                                           (setq iii (+ 1 iii))
                                      )
                                     (setq ttt (subst p5110 (nth iii ttt) ttt))
                                     (entmod ttt)
                             ))

                      )
                        ((= JJJ "设计号") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p4110 (list 10 (car p41) (cadr P41) 0))
                                     (setq p4111 (list 11 (car p41) (cadr P41) 0)) 
                                     (while (/= 11 (car (nth iii ttt)))
                                           (setq iii (+ 1 iii))
                                      )
                                     (setq ttt (subst p4111 (nth iii ttt) ttt))
                                     (setq iii (+ 1 iii))
                                     (while (/= 11 (car (nth iii ttt)))
                                           (setq iii (+ 1 iii))
                                      )
                                     (setq ttt (subst p4111 (nth iii ttt) ttt))
                                     (setq iii (+ 1 iii))
                                     (while (/= 10 (car (nth iii ttt)))
                                           (setq iii (+ 1 iii))
                                      )
                                     (setq ttt (subst p4110 (nth iii ttt) ttt))
                                     (entmod ttt)
                             ))

                      )

                        ((= JJJ "设计阶段") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p4210 (list 10 (car p42) (cadr P42) 0))
                                     (setq p4211 (list 11 (car p42) (cadr P42) 0)) 
                                     (while (/= 11 (car (nth iii ttt)))
                                           (setq iii (+ 1 iii))
                                      )
                                     (setq ttt (subst p4211 (nth iii ttt) ttt))
                                     (setq iii (+ 1 iii))
                                     (while (/= 11 (car (nth iii ttt)))
                                           (setq iii (+ 1 iii))
                                      )
                                     (setq ttt (subst p4211 (nth iii ttt) ttt))
                                     (setq iii (+ 1 iii))
                                     (while (/= 10 (car (nth iii ttt)))
                                           (setq iii (+ 1 iii))
                                      )
                                     (setq ttt (subst p4210 (nth iii ttt) ttt))
                                     (entmod ttt)
                             ))

                      )

                        ((= JJJ "版本") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p4310 (list 10 (car p43) (cadr P43) 0))
                                     (setq p4311 (list 11 (car p43) (cadr P43) 0)) 
                                     (while (/= 11 (car (nth iii ttt)))
                                           (setq iii (+ 1 iii))
                                      )
                                     (setq ttt (subst p4311 (nth iii ttt) ttt))
                                     (setq iii (+ 1 iii))
                                     (while (/= 11 (car (nth iii ttt)))
                                           (setq iii (+ 1 iii))
                                      )
                                     (setq ttt (subst p4311 (nth iii ttt) ttt))
                                     (setq iii (+ 1 iii))
                                     (while (/= 10 (car (nth iii ttt)))
                                           (setq iii (+ 1 iii))
                                      )
                                     (setq ttt (subst p4310 (nth iii ttt) ttt))
                                     (entmod ttt)
                             ))

                      )

                        ((= JJJ "专业") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p5210 (list 10 (car p52) (cadr P52) 0))
                                     (setq p5211 (list 11 (car p52) (cadr P52) 0)) 
                                     (while (/= 11 (car (nth iii ttt)))
                                           (setq iii (+ 1 iii))
                                      )
                                     (setq ttt (subst p5211 (nth iii ttt) ttt))
                                     (setq iii (+ 1 iii))
                                     (while (/= 11 (car (nth iii ttt)))
                                           (setq iii (+ 1 iii))
                                      )
                                     (setq ttt (subst p5211 (nth iii ttt) ttt))
                                     (setq iii (+ 1 iii))
                                     (while (/= 10 (car (nth iii ttt)))
                                           (setq iii (+ 1 iii))
                                      )
                                     (setq ttt (subst p5210 (nth iii ttt) ttt))
                                     (entmod ttt)
                             ))

                      )

                        ((= JJJ "日期") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p5310 (list 10 (car p53) (cadr P53) 0))
                                     (setq p5311 (list 11 (car p53) (cadr P53) 0)) 
                                     (while (/= 11 (car (nth iii ttt)))
                                           (setq iii (+ 1 iii))
                                      )
                                     (setq ttt (subst p5311 (nth iii ttt) ttt))
                                     (setq iii (+ 1 iii))
                                     (while (/= 11 (car (nth iii ttt)))
                                           (setq iii (+ 1 iii))
                                      )
                                     (setq ttt (subst p5311 (nth iii ttt) ttt))
                                     (setq iii (+ 1 iii))
                                     (while (/= 10 (car (nth iii ttt)))
                                           (setq iii (+ 1 iii))
                                      )
                                     (setq ttt (subst p5310 (nth iii ttt) ttt))
                                     (entmod ttt)
                             ))

                      )

                        ((= JJJ "审定") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p1110 (list 10 (car p11) (cadr P11) 0))
                                     (setq p1111 (list 11 (car p11) (cadr P11) 0)) 
                                     (while (/= 11 (car (nth iii ttt)))
                                           (setq iii (+ 1 iii))
                                      )
                                     (setq ttt (subst p1111 (nth iii ttt) ttt))
                                     (setq iii (+ 1 iii))
                                     (while (/= 11 (car (nth iii ttt)))
                                           (setq iii (+ 1 iii))
                                      )
                                     (setq ttt (subst p1111 (nth iii ttt) ttt))
                                     (setq iii (+ 1 iii))
                                     (while (/= 10 (car (nth iii ttt)))
                                           (setq iii (+ 1 iii))
                                      )
                                     (setq ttt (subst p1110 (nth iii ttt) ttt))
                                     (entmod ttt)
                             ))

                      )

                        ((= JJJ "审核") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p2110 (list 10 (car p21) (cadr P21) 0))
                                     (setq p2111 (list 11 (car p21) (cadr P21) 0)) 
                                     (while (/= 11 (car (nth iii ttt)))
                                           (setq iii (+ 1 iii))
                                      )
                                     (setq ttt (subst p2111 (nth iii ttt) ttt))
                                     (setq iii (+ 1 iii))
                                     (while (/= 11 (car (nth iii ttt)))
                                           (setq iii (+ 1 iii))
                                      )
                                     (setq ttt (subst p2111 (nth iii ttt) ttt))
                                     (setq iii (+ 1 iii))
                                     (while (/= 10 (car (nth iii ttt)))
                                           (setq iii (+ 1 iii))
                                      )
                                     (setq ttt (subst p2110 (nth iii ttt) ttt))
                                     (entmod ttt)
                             ))

                      )

                        ((= JJJ "项目负责人") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p3110 (list 10 (car p31) (cadr P31) 0))
                                     (setq p3111 (list 11 (car p31) (cadr P31) 0)) 
                                     (while (/= 11 (car (nth iii ttt)))
                                           (setq iii (+ 1 iii))
                                      )
                                     (setq ttt (subst p3111 (nth iii ttt) ttt))
                                     (setq iii (+ 1 iii))
                                     (while (/= 11 (car (nth iii ttt)))
                                           (setq iii (+ 1 iii))
                                      )
                                     (setq ttt (subst p3111 (nth iii ttt) ttt))
                                     (setq iii (+ 1 iii))
                                     (while (/= 10 (car (nth iii ttt)))
                                           (setq iii (+ 1 iii))
                                      )
                                     (setq ttt (subst p3110 (nth iii ttt) ttt))
                                     (entmod ttt)
                             ))

                      )

                        ((= JJJ "专业负责人") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p1210 (list 10 (car p12) (cadr P12) 0))
                                     (setq p1211 (list 11 (car p12) (cadr P12) 0)) 
                                     (while (/= 11 (car (nth iii ttt)))
                                           (setq iii (+ 1 iii))
                                      )
                                     (setq ttt (subst p1211 (nth iii ttt) ttt))
                                     (setq iii (+ 1 iii))
                                     (while (/= 11 (car (nth iii ttt)))
                                           (setq iii (+ 1 iii))
                                      )
                                     (setq ttt (subst p1211 (nth iii ttt) ttt))
                                     (setq iii (+ 1 iii))
                                     (while (/= 10 (car (nth iii ttt)))
                                           (setq iii (+ 1 iii))
                                      )
                                     (setq ttt (subst p1210 (nth iii ttt) ttt))
                                     (entmod ttt)
                             ))

                      )

                        ((= JJJ "校核") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p2210 (list 10 (car p22) (cadr P22) 0))
                                     (setq p2211 (list 11 (car p22) (cadr P22) 0)) 
                                     (while (/= 11 (car (nth iii ttt)))
                                           (setq iii (+ 1 iii))
                                      )
                                     (setq ttt (subst p2211 (nth iii ttt) ttt))
                                     (setq iii (+ 1 iii))
                                     (while (/= 11 (car (nth iii ttt)))
                                           (setq iii (+ 1 iii))
                                      )
                                     (setq ttt (subst p2211 (nth iii ttt) ttt))
                                     (setq iii (+ 1 iii))
                                     (while (/= 10 (car (nth iii ttt)))
                                           (setq iii (+ 1 iii))
                                      )
                                     (setq ttt (subst p2210 (nth iii ttt) ttt))
                                     (entmod ttt)
                             ))

                      )
                        ((= JJJ "设计") 
                               (setq iii 0)
                               (while (/= 10 (car (nth iii ttt)))
                                      (setq iii (+ 1 iii))
                               )
                               (if (<= iii 15) 
                                   (progn 
                                     (setq P101 (cdr (nth iii ttt)))
                                     (setq ttt (vl-remove p101 ttt))  ;去掉多余的误导定位点
                                     (setq p3210 (list 10 (car p32) (cadr P32) 0))
                                     (setq p3211 (list 11 (car p32) (cadr P32) 0)) 
                                     (while (/= 11 (car (nth iii ttt)))
                                           (setq iii (+ 1 iii))
                                      )
                                     (setq ttt (subst p3211 (nth iii ttt) ttt))
                                     (setq iii (+ 1 iii))
                                     (while (/= 11 (car (nth iii ttt)))
                                           (setq iii (+ 1 iii))
                                      )
                                     (setq ttt (subst p3211 (nth iii ttt) ttt))
                                     (setq iii (+ 1 iii))
                                     (while (/= 10 (car (nth iii ttt)))
                                           (setq iii (+ 1 iii))
                                      )
                                     (setq ttt (subst p3210 (nth iii ttt) ttt))
                                     (entmod ttt)
                             ))

                      )
                  )
                 (entupd mst)
           )
          (setq snn (+ 1 snn))
     ) 
       (setvar "OSMODE" OA_osm)
)

;|*****************************************************************************
工程设计OA图框DCL对话框功能子程序:图纸图框助手对话框主程序
20200410
--引用全局变量   Meaad_all_scale  MEAAD_AZML_V31 
|;
;;*****************************************************************************
(DEFUN DHK_OATKSCZS (/ dcl_EAAD)
    (if  (= Meaad_all_scale nil) (setq meaad_all_scale (getint "\n出图比例因数Meaad_all_scale还没有定义，请输入1：<1,100,200,1000>：")))
    (if  (= Meaad_all_scale nil) (setq meaad_all_scale 1))
    (if (= MEAAD_AZML_V31 nil) 
            (progn  (alert "软件安装位置全局变量MEAAD_AZML_V31没有定义!") (exit)))
    (setq MEAAD_TKKIND (getint "\n选择图框类型 1-标准 2-大项目 <1>:"))
    (if (= nil MEAAD_TKKIND) (setq MEAAD_TKKIND 1))
    (cond ((= MEAAD_TKKIND 1) (setq MEAAD_CRTKNAME "OA图框_A2_594_横框_标准"))
          ((= MEAAD_TKKIND 2) (setq MEAAD_CRTKNAME "OA图框_A2_594_横框_大项目"))
    )
    (setq dcl_EAAD (load_dialog "Meaad_OATK_3.0.dcl"))
    (if (not  (new_dialog "MEAAD3_OA_TZTKSCZS" dcl_EAAD))  (exit))
    (action_tile "DHK_TZTK_DQQJ"     "(done_dialog 1)  (unload_dialog dcl_EAAD)")
    (action_tile "DHK_TZTK_DQHV"     "(done_dialog 2)  (unload_dialog dcl_EAAD)")
    (action_tile "DHK_TZTK_DQSCGZW"  "(done_dialog 3)  (unload_dialog dcl_EAAD)")
    (action_tile "DHK_TZTK_DQFZGZW"  "(done_dialog 4)  (unload_dialog dcl_EAAD)")
    (action_tile "DHK_TZTK_DQXF"     "(done_dialog 5)  (unload_dialog dcl_EAAD)")

    (action_tile "DHK_TZTK_ZKQJ"   "(done_dialog 6)  (unload_dialog dcl_EAAD)")
    (action_tile "DHK_TZTK_ZKSBKZ" "(done_dialog 7)  (unload_dialog dcl_EAAD)")
    (action_tile "DHK_TZTK_ZKYBJC" "(done_dialog 8)  (unload_dialog dcl_EAAD)")
    (action_tile "DHK_TZTK_ZKHJJK"  "(done_dialog 9)  (unload_dialog dcl_EAAD)")
    (action_tile "DHK_TZTK_ZKBZT"  "(done_dialog 10)  (unload_dialog dcl_EAAD)")

    (action_tile "DHK_TZTK_CBSJ" "(done_dialog 11)  (unload_dialog dcl_EAAD)")
    (action_tile "cancel" "(done_dialog 0)  (unload_dialog dcl_EAAD)")
    (setq dd (start_dialog))
    (cond ((= dd 1) (DHK_TZTKDQQJ))
          ((= dd 2) (DHK_TZTKDQHV))
          ((= dd 3) (DHK_TZTKDQSCGZW))
          ((= dd 4) (DHK_TZTKDQFZGZW))
          ((= dd 5) (DHK_TZTKDQXF))
          ((= dd 6) (DHK_TZTKZKQJ))
          ((= dd 7) (DHK_TZTKZKSBKZ))
          ((= dd 8) (DHK_TZTKZKYBJC))
          ((= dd 9) (DHK_TZTKZKHJJK))
          ((= dd 10) (DHK_TZTKZKBZT))
          ((= dd 11) (DHK_TZTKCBSJ))
    )
)


;|*****************************************************************************
工程设计OA图纸图框助手:电气全局设计对话框DCL主程序
20200410
|;
;;*****************************************************************************
(DEFUN DHK_TZTKDQQJ (/ dcl_EAAD a11 a12 a13 a14 a15 a21 a22 a23 a24 a25 dd) 
    (setq dcl_EAAD (load_dialog "Meaad_OATK_3.0.dcl"))
    (if (not  (new_dialog "MEAAD3_TZTK_DQQJL" dcl_EAAD))  (exit))
    (action_tile "DHK_TZTK_INSERT" "(DHK_TZTK_DQQJRDDCL) (done_dialog 1)  (unload_dialog dcl_EAAD)")
    (action_tile "cancel" "(done_dialog 0)  (unload_dialog dcl_EAAD)")
    (setq dd (start_dialog))
    (if (= dd 1) (DHK_TZTKDQQJINSERT))
)


;|*****************************************************************************
工程设计OA图纸图框助手:电气全局设计(读DCL数据）
20200410
|;
;;*****************************************************************************
(DEFUN DHK_TZTK_DQQJRDDCL () 
        (setq a11 (get_tile "OATKZS_ZSM"))
        (setq a12 (get_tile "OATKZS_JNZP"))
        (setq a13 (get_tile "OATKZS_FZZP"))
        (setq a14 (get_tile "OATKZS_FLJDZP"))
        (setq a15 (get_tile "OATKZS_XFZP"))
        (setq a21 (get_tile "OATKZS_ZMZP"))
        (setq a22 (get_tile "OATKZS_SGZP"))
        (setq a23 (get_tile "OATKZS_XMDHFJB"))
        (setq a24 (get_tile "OATKZS_SBCLB"))
        (setq a25 (get_tile "OATKZS_SBHZB"))
)

;|*****************************************************************************
工程设计OA图纸图框助手:电气全局设计（图框插入）
20200410
|;
;;*****************************************************************************
(DEFUN DHK_TZTKDQQJINSERT (/ p OA_osm ) 
        (setq OA_osm (getvar "OSMODE"))
        (setvar "OSMODE" 0)
        (setq p (getpoint "\n图框插入点："))
        (if (= a11 "1")  (progn
              (command "insert"MEAAD_CRTKNAME p meaad_all_scale meaad_all_scale 0  "explode" "L")
              (OAPUT_oneatt (entlast) "图名" "电气施工图设计总说明")
              (OAPUT_oneatt (entlast) "图号" "SDQ9999-999")
              (setq p (polar p (dtr 270) (* 600 meaad_all_scale)))
        ))
        (if (= a12 "1")  (progn
              (command "insert" MEAAD_CRTKNAME p meaad_all_scale meaad_all_scale 0  "explode" "L")
              (OAPUT_oneatt (entlast) "图名" "电气施工图设计说明（节能专篇）")
              (OAPUT_oneatt (entlast) "图号" "SDQ9999-999")
              (setq p (polar p (dtr 270) (* 600 meaad_all_scale)))
        ))
        (if (= a13 "1")  (progn
              (command "insert" MEAAD_CRTKNAME p meaad_all_scale meaad_all_scale 0  "explode" "L")
              (OAPUT_oneatt (entlast) "图名" "电气施工图设计说明（防震专篇）")
              (OAPUT_oneatt (entlast) "图号" "SDQ9999-999")
              (setq p (polar p (dtr 270) (* 600 meaad_all_scale)))
        ))
        (if (= a14 "1")  (progn
              (command "insert" MEAAD_CRTKNAME p meaad_all_scale meaad_all_scale 0  "explode" "L")
              (OAPUT_oneatt (entlast) "图名" "电气施工图设计说明（防雷专篇）")
              (OAPUT_oneatt (entlast) "图号" "SDQ9999-999")
              (setq p (polar p (dtr 270) (* 600 meaad_all_scale)))
        ))
        (if (= a15 "1")  (progn
              (command "insert" MEAAD_CRTKNAME p meaad_all_scale meaad_all_scale 0  "explode" "L")
              (OAPUT_oneatt (entlast) "图名" "电气施工图设计说明（消防专篇）")
              (OAPUT_oneatt (entlast) "图号" "SDQ9999-999")
              (setq p (polar p (dtr 270) (* 600 meaad_all_scale)))
        ))
        (if (= a21 "1")  (progn
              (command "insert"  MEAAD_CRTKNAME p meaad_all_scale meaad_all_scale 0  "explode" "L")
              (OAPUT_oneatt (entlast) "图名" "电气施工图设计说明（照明专篇）")
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0  "explode" "L")
              (OAPUT_oneatt (entlast) "图名" "电气施工图设计说明（五防专篇）")
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" "电气施工图设计说明（施工专篇）")
              (OAPUT_oneatt (entlast) "图号" "SDQ9999-999")
              (setq p (polar p (dtr 270) (* 600 meaad_all_scale)))
        ))
        (if (= a24 "1")  (progn
              (command "insert"  MEAAD_CRTKNAME p meaad_all_scale meaad_all_scale 0  "explode" "L")
              (OAPUT_oneatt (entlast) "图名" "项目代号分解表")
              (OAPUT_oneatt (entlast) "图号" "SDQ9999-999")
              (setq p (polar p (dtr 270) (* 600 meaad_all_scale)))
        ))
        (if (= a25 "1")  (progn
              (command "insert"  MEAAD_CRTKNAME p meaad_all_scale meaad_all_scale 0  "explode" "L")
              (OAPUT_oneatt (entlast) "图名" "主要电气设备材料汇总表")
              (OAPUT_oneatt (entlast) "图号" "SDQ9999-999")
              (setq p (polar p (dtr 270) (* 600 meaad_all_scale)))
        ))
       (setvar "OSMODE" OA_osm)
)



;|*****************************************************************************
工程设计OA图纸图框助手:电气高压系统设计对话框DCL主程序
20200410
|;
;;*****************************************************************************
(DEFUN DHK_TZTKDQHV (/ dcl_EAAD a11 a12 a13 a14 dd) 
    (setq dcl_EAAD (load_dialog "Meaad_OATK_3.0.dcl"))
    (if (not  (new_dialog "MEAAD3_TZTK_DQHVL" dcl_EAAD))  (exit))
    (action_tile "DHK_TZTK_INSERT" "(DHK_TZTK_HVRDDCL) (done_dialog 1)  (unload_dialog dcl_EAAD)")
    (action_tile "cancel" "(done_dialog 0)  (unload_dialog dcl_EAAD)")
    (setq dd (start_dialog))
    (if (= dd 1) (DHK_TZTKHVINSERT))
)


;|*****************************************************************************
工程设计OA图纸图框助手:高压系统设计(读DCL数据）
20200410
|;
;;*****************************************************************************
(DEFUN DHK_TZTK_HVRDDCL () 
        (setq a11 (get_tile "OATKZS_GYXT"))
        (setq a12 (get_tile "OATKZS_DYMP"))
        (setq a13 (get_tile "OATKZS_DLJK"))
        (setq a14 (get_tile "OATKZS_ZLDY"))
)

;|*****************************************************************************
工程设计OA图纸图框助手:高压系统设计（图框插入）
20200410
|;
;;*****************************************************************************
(DEFUN DHK_TZTKHVINSERT (/ p OA_osm) 
        (setq OA_osm (getvar "OSMODE"))
        (setvar "OSMODE" 0)
        (setq p (getpoint "\n图框插入点："))
        (if (= a11 "1")  (progn
              (command "insert"  MEAAD_CRTKNAME p meaad_all_scale meaad_all_scale 0  "explode" "L")
              (OAPUT_oneatt (entlast) "图名" "10kV高压配电系统图")
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" "10kV高压开关柜电压小母线设计图")
              (OAPUT_oneatt (entlast) "图号" "SDQ9999-999")
              (setq p (polar p (dtr 270) (* 600 meaad_all_scale)))
        ))
        (if (= a13 "1")  (progn
              (command "insert"  MEAAD_CRTKNAME p meaad_all_scale meaad_all_scale 0  "explode" "L")
              (OAPUT_oneatt (entlast) "图名" "电力监控系统技术要求图")
              (OAPUT_oneatt (entlast) "图号" "SDQ9999-999")
              (setq p (polar p (dtr 270) (* 600 meaad_all_scale)))
        ))
        (if (= a14 "1")  (progn
              (command "insert"  MEAAD_CRTKNAME p meaad_all_scale meaad_all_scale 0  "explode" "L")
              (OAPUT_oneatt (entlast) "图名" "直流屏技术要求图")
              (OAPUT_oneatt (entlast) "图号" "SDQ9999-999")
              (setq p (polar p (dtr 270) (* 600 meaad_all_scale)))
        ))
       (setvar "OSMODE" OA_osm)
)


;|*****************************************************************************
工程设计OA图纸图框助手:生产构筑物设计对话框DCL主程序
20200410
|;
;;*****************************************************************************
(DEFUN DHK_TZTKDQSCGZW (/ dcl_EAAD a11 a12 a13 a14 a15 a16 a21 a22 a23 a24 a25 a26 gzw_name dd) 
    (setq dcl_EAAD (load_dialog "Meaad_OATK_3.0.dcl"))
    (if (not  (new_dialog "MEAAD3_TZTK_DQSCGZWL" dcl_EAAD))  (exit))
    (action_tile "DHK_TZTK_SCINSERT" "(DHK_TZTK_SCGZWRDDCL) (done_dialog 1)  (unload_dialog dcl_EAAD)")
    (action_tile "cancel" "(done_dialog 0)  (unload_dialog dcl_EAAD)")
    (setq dd (start_dialog))
    (if (= dd 1) (DHK_TZTKSCGZWINSERT))
)


;|*****************************************************************************
工程设计OA图纸图框助手:生产构筑物设计(读DCL数据）
20200410
|;
;;*****************************************************************************
(DEFUN DHK_TZTK_SCGZWRDDCL () 
        (setq a11 (get_tile "OATKZS_SC_MNS"))
        (setq a12 (get_tile "OATKZS_SC_MCC"))
        (setq a13 (get_tile "OATKZS_SC_AP"))
        (setq a14 (get_tile "OATKZS_SC_UPS"))
        (setq a15 (get_tile "OATKZS_SC_EPS"))
        (setq a16 (get_tile "OATKZS_SC_AC"))
        (setq a21 (get_tile "OATKZS_SC_AB"))
        (setq a22 (get_tile "OATKZS_SC_DLB"))
        (setq a23 (get_tile "OATKZS_SC_DLBZT"))
        (setq a24 (get_tile "OATKZS_SC_ZMBZT"))
        (setq a25 (get_tile "OATKZS_SC_FLBZT"))
        (setq a26 (get_tile "OATKZS_SC_SBCLB"))
        (setq gzw_name (get_tile "OATKZS_SC_NAME"))
)

;|*****************************************************************************
工程设计OA图纸图框助手:生产构筑物设计（图框插入）
20200410
|;
;;*****************************************************************************
(DEFUN DHK_TZTKSCGZWINSERT (/ p OA_osm ) 
        (setq OA_osm (getvar "OSMODE"))
        (setvar "OSMODE" 0)
        (setq p (getpoint "\n图框插入点："))
        (if (= a26 "1")  (progn
              (command "insert"  MEAAD_CRTKNAME p meaad_all_scale meaad_all_scale 0 "explode" "L")
              (OAPUT_oneatt (entlast) "图名" (strcat gzw_name "项目代号分解及设备材料表"))
              (OAPUT_oneatt (entlast) "图号" "SDQ9999-999")
              (setq p (polar p (dtr 270) (* 600 meaad_all_scale)))
        ))
        (if (= a11 "1")  (progn
              (command "insert"  MEAAD_CRTKNAME p meaad_all_scale meaad_all_scale 0 "explode" "L")
              (OAPUT_oneatt (entlast) "图名" (strcat gzw_name "低压开关柜配电系统图"))
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" (strcat gzw_name "低压MCC柜配电系统图"))
              (OAPUT_oneatt (entlast) "图号" "SDQ9999-999")
              (setq p (polar p (dtr 270) (* 600 meaad_all_scale)))
        ))
        (if (= a13 "1")  (progn
              (command "insert"  MEAAD_CRTKNAME p meaad_all_scale meaad_all_scale 0 "explode" "L")
              (OAPUT_oneatt (entlast) "图名" (strcat gzw_name "低压动力柜（箱）配电系统图"))
              (OAPUT_oneatt (entlast) "图号" "SDQ9999-999")
              (setq p (polar p (dtr 270) (* 600 meaad_all_scale)))
        ))
        (if (= a14 "1")  (progn
              (command "insert"  MEAAD_CRTKNAME p meaad_all_scale meaad_all_scale 0 "explode" "L")
              (OAPUT_oneatt (entlast) "图名" (strcat gzw_name "UPS不间断电源柜配电系统图"))
              (OAPUT_oneatt (entlast) "图号" "SDQ9999-999")
              (setq p (polar p (dtr 270) (* 600 meaad_all_scale)))
        ))
        (if (= a15 "1")  (progn
              (command "insert"  MEAAD_CRTKNAME p meaad_all_scale meaad_all_scale 0 "explode" "L")
              (OAPUT_oneatt (entlast) "图名" (strcat gzw_name "EPS应急电源柜配电系统图"))
              (OAPUT_oneatt (entlast) "图号" "SDQ9999-999")
              (setq p (polar p (dtr 270) (* 600 meaad_all_scale)))
        ))
        (if (= a16 "1")  (progn
              (command "insert"  MEAAD_CRTKNAME p meaad_all_scale meaad_all_scale 0 "explode" "L")
              (OAPUT_oneatt (entlast) "图名" (strcat gzw_name "电控装置技术要求一览表"))
              (OAPUT_oneatt (entlast) "图号" "SDQ9999-999")
              (setq p (polar p (dtr 270) (* 600 meaad_all_scale)))
        ))
        (if (= a21 "1")  (progn
              (command "insert"  MEAAD_CRTKNAME p meaad_all_scale meaad_all_scale 0  "explode" "L")
              (OAPUT_oneatt (entlast) "图名" (strcat gzw_name "现场按钮箱技术要求一览表"))
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0 "explode" "L")
              (OAPUT_oneatt (entlast) "图名" (strcat gzw_name "电缆配置表"))
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" (strcat gzw_name "动力布置图"))
              (OAPUT_oneatt (entlast) "图号" "SDQ9999-999")
              (setq p (polar p (dtr 270) (* 600 meaad_all_scale)))
        ))
        (if (= a24 "1")  (progn
              (command "insert"  MEAAD_CRTKNAME p meaad_all_scale meaad_all_scale 0  "explode" "L")
              (OAPUT_oneatt (entlast) "图名" (strcat gzw_name "照明布置图"))
              (OAPUT_oneatt (entlast) "图号" "SDQ9999-999")
              (setq p (polar p (dtr 270) (* 600 meaad_all_scale)))
        ))
        (if (= a25 "1")  (progn
              (command "insert"  MEAAD_CRTKNAME p meaad_all_scale meaad_all_scale 0  "explode" "L")
              (OAPUT_oneatt (entlast) "图名" (strcat gzw_name "防雷接地及等电位联结布置图"))
              (OAPUT_oneatt (entlast) "图号" "SDQ9999-999")
              (setq p (polar p (dtr 270) (* 600 meaad_all_scale)))
        ))
       (setvar "OSMODE" OA_osm)
)

;|*****************************************************************************
工程设计OA图纸图框助手:辅助构筑物设计对话框DCL主程序
20200410
|;
;;*****************************************************************************
(DEFUN DHK_TZTKDQFZGZW (/ dcl_EAAD a11 a12 a13 a14 a15 a21 a22 a23 a24 a25 gzw_name dd) 
    (setq dcl_EAAD (load_dialog "Meaad_OATK_3.0.dcl"))
    (if (not  (new_dialog "MEAAD3_TZTK_DQFZGZWL" dcl_EAAD))  (exit))
    (action_tile "DHK_TZTK_FZINSERT" "(DHK_TZTK_FZGZWRDDCL) (done_dialog 1)  (unload_dialog dcl_EAAD)")
    (action_tile "cancel" "(done_dialog 0)  (unload_dialog dcl_EAAD)")
    (setq dd (start_dialog))
    (if (= dd 1) (DHK_TZTKFZGZWINSERT))
)


;|*****************************************************************************
工程设计OA图纸图框助手:辅助构筑物设计(读DCL数据）
20200410
|;
;;*****************************************************************************
(DEFUN DHK_TZTK_FZGZWRDDCL () 
        (setq a11 (get_tile "OATKZS_FZ_SMSBB"))
        (setq a12 (get_tile "OATKZS_FZ_ZMPD"))
        (setq a13 (get_tile "OATKZS_FZ_ZMKZ"))
        (setq a14 (get_tile "OATKZS_FZ_ZNFW"))
        (setq a15 (get_tile "OATKZS_FZ_ZMBZT"))
        (setq a21 (get_tile "OATKZS_FZ_CZBZT"))
        (setq a22 (get_tile "OATKZS_FZ_YJZM"))
        (setq a23 (get_tile "OATKZS_FZ_CATV"))
        (setq a24 (get_tile "OATKZS_FZ_ZHBX"))
        (setq a25 (get_tile "OATKZS_FZ_FLJD"))
        (setq gzw_name (get_tile "OATKZS_FZ_NAME"))
)

;|*****************************************************************************
工程设计OA图纸图框助手:辅助构筑物设计（图框插入）
20200410
|;
;;*****************************************************************************
(DEFUN DHK_TZTKFZGZWINSERT (/ p OA_osm ) 
        (setq OA_osm (getvar "OSMODE"))
        (setvar "OSMODE" 0)
        (setq p (getpoint "\n图框插入点："))
        (if (= a11 "1")  (progn
              (command "insert"  MEAAD_CRTKNAME p meaad_all_scale meaad_all_scale 0  "explode" "L")
              (OAPUT_oneatt (entlast) "图名" (strcat gzw_name "电气设计说明及设备材料表"))
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" (strcat gzw_name "照明配电系统图"))
              (OAPUT_oneatt (entlast) "图号" "SDQ9999-999")
              (setq p (polar p (dtr 270) (* 600 meaad_all_scale)))
        ))
        (if (= a13 "1")  (progn
              (command "insert"  MEAAD_CRTKNAME p meaad_all_scale meaad_all_scale 0  "explode" "L")
              (OAPUT_oneatt (entlast) "图名" (strcat gzw_name "智能照明控制系统图"))
              (OAPUT_oneatt (entlast) "图号" "SDQ9999-999")
              (setq p (polar p (dtr 270) (* 600 meaad_all_scale)))
        ))
        (if (= a14 "1")  (progn
              (command "insert"  MEAAD_CRTKNAME p meaad_all_scale meaad_all_scale 0  "explode" "L")
              (OAPUT_oneatt (entlast) "图名" (strcat gzw_name "智能化服务系统图"))
              (OAPUT_oneatt (entlast) "图号" "SDQ9999-999")
              (setq p (polar p (dtr 270) (* 600 meaad_all_scale)))
        ))
        (if (= a15 "1")  (progn
              (command "insert"  MEAAD_CRTKNAME p meaad_all_scale meaad_all_scale 0  "explode" "L")
              (OAPUT_oneatt (entlast) "图名" (strcat gzw_name "照明布置图"))
              (OAPUT_oneatt (entlast) "图号" "SDQ9999-999")
              (setq p (polar p (dtr 270) (* 600 meaad_all_scale)))
        ))
        (if (= a21 "1")  (progn
              (command "insert"  MEAAD_CRTKNAME p meaad_all_scale meaad_all_scale 0  "explode" "L")
              (OAPUT_oneatt (entlast) "图名" (strcat gzw_name "应急照明布置图"))
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0  "explode" "L")
              (OAPUT_oneatt (entlast) "图名" (strcat gzw_name "插座布置图"))
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" (strcat gzw_name "有线电视布置图"))
              (OAPUT_oneatt (entlast) "图号" "SDQ9999-999")
              (setq p (polar p (dtr 270) (* 600 meaad_all_scale)))
        ))
        (if (= a24 "1")  (progn
              (command "insert"  MEAAD_CRTKNAME p meaad_all_scale meaad_all_scale 0  "explode" "L")
              (OAPUT_oneatt (entlast) "图名" (strcat gzw_name "综合布线布置图"))
              (OAPUT_oneatt (entlast) "图号" "SDQ9999-999")
              (setq p (polar p (dtr 270) (* 600 meaad_all_scale)))
        ))
        (if (= a25 "1")  (progn
              (command "insert"  MEAAD_CRTKNAME p meaad_all_scale meaad_all_scale 0  "explode" "L")
              (OAPUT_oneatt (entlast) "图名" (strcat gzw_name "防雷接地及等电位联结布置图"))
              (OAPUT_oneatt (entlast) "图号" "SDQ9999-999")
              (setq p (polar p (dtr 270) (* 600 meaad_all_scale)))
        ))
       (setvar "OSMODE" OA_osm)
)



;|*****************************************************************************
工程设计OA图纸图框助手:消防设计对话框DCL主程序
20200410
|;
;;*****************************************************************************
(DEFUN DHK_TZTKDQXF (/ dcl_EAAD a11 a12 a13 a14 a21 a22 a23 a24 gzw_name dd) 
    (setq dcl_EAAD (load_dialog "Meaad_OATK_3.0.dcl"))
    (if (not  (new_dialog "MEAAD3_TZTK_DQXFSJ" dcl_EAAD))  (exit))
    (action_tile "DHK_TZTK_XFINSERT" "(DHK_TZTK_XFRDDCL) (done_dialog 1)  (unload_dialog dcl_EAAD)")
    (action_tile "cancel" "(done_dialog 0)  (unload_dialog dcl_EAAD)")
    (setq dd (start_dialog))
    (if (= dd 1) (DHK_TZTKXFINSERT))
)


;|*****************************************************************************
工程设计OA图纸图框助手:消防构筑物设计(读DCL数据）
20200410
|;
;;*****************************************************************************
(DEFUN DHK_TZTK_XFRDDCL () 
        (setq a11 (get_tile "OATKZS_XF_SM"))
        (setq a12 (get_tile "OATKZS_XF_SBB"))
        (setq a13 (get_tile "OATKZS_XF_PDXT"))
        (setq a14 (get_tile "OATKZS_XF_SBYQ"))
        (setq a21 (get_tile "OATKZS_XF_HZBJ"))
        (setq a22 (get_tile "OATKZS_XF_DLB"))
        (setq a23 (get_tile "OATKZS_XF_HZBJBZT"))
        (setq a24 (get_tile "OATKZS_XF_YJZMBZT"))
        (setq gzw_name (get_tile "OATKZS_XF_NAME"))
)

;|*****************************************************************************
工程设计OA图纸图框助手:消防设计（图框插入）
20200410
|;
;;*****************************************************************************
(DEFUN DHK_TZTKXFINSERT (/ p OA_osm ) 
        (setq OA_osm (getvar "OSMODE"))
        (setvar "OSMODE" 0)
        (setq p (getpoint "\n图框插入点："))
        (if (= a11 "1")  (progn
              (command "insert"  MEAAD_CRTKNAME p meaad_all_scale meaad_all_scale 0  "explode" "L")
              (OAPUT_oneatt (entlast) "图名" (strcat gzw_name "消防电气设计说明"))
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" (strcat gzw_name "消防电气项目代号分解及设备材料表"))
              (OAPUT_oneatt (entlast) "图号" "SDQ9999-999")
              (setq p (polar p (dtr 270) (* 600 meaad_all_scale)))
        ))
        (if (= a13 "1")  (progn
              (command "insert"  MEAAD_CRTKNAME p meaad_all_scale meaad_all_scale 0  "explode" "L")
              (OAPUT_oneatt (entlast) "图名" (strcat gzw_name "消防配电系统图"))
              (OAPUT_oneatt (entlast) "图号" "SDQ9999-999")
              (setq p (polar p (dtr 270) (* 600 meaad_all_scale)))
        ))
        (if (= a14 "1")  (progn
              (command "insert"  MEAAD_CRTKNAME p meaad_all_scale meaad_all_scale 0  "explode" "L")
              (OAPUT_oneatt (entlast) "图名" (strcat gzw_name "消防电气设备要求一览表"))
              (OAPUT_oneatt (entlast) "图号" "SDQ9999-999")
              (setq p (polar p (dtr 270) (* 600 meaad_all_scale)))
        ))
        (if (= a21 "1")  (progn
              (command "insert"  MEAAD_CRTKNAME p meaad_all_scale meaad_all_scale 0  "explode" "L")
              (OAPUT_oneatt (entlast) "图名" (strcat gzw_name "火灾自动报警系统图"))
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0  "explode" "L")
              (OAPUT_oneatt (entlast) "图名" (strcat gzw_name "消防电缆配置表"))
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" (strcat gzw_name "火灾自动报警布置图"))
              (OAPUT_oneatt (entlast) "图号" "SDQ9999-999")
              (setq p (polar p (dtr 270) (* 600 meaad_all_scale)))
        ))
        (if (= a24 "1")  (progn
              (command "insert"  MEAAD_CRTKNAME p meaad_all_scale meaad_all_scale 0  "explode" "L")
              (OAPUT_oneatt (entlast) "图名" (strcat gzw_name "火灾应急照明布置图"))
              (OAPUT_oneatt (entlast) "图号" "SDQ9999-999")
              (setq p (polar p (dtr 270) (* 600 meaad_all_scale)))
        ))
       (setvar "OSMODE" OA_osm)
)

;|*****************************************************************************
工程设计OA图纸图框助手:智能化全局设计对话框DCL主程序
20200410
|;
;;*****************************************************************************
(DEFUN DHK_TZTKZKQJ (/ dcl_EAAD a11 a12 a13 a21 a22 a23 gzw_name dd) 
    (setq dcl_EAAD (load_dialog "Meaad_OATK_3.0.dcl"))
    (if (not  (new_dialog "MEAAD3_TZTK_ZNHQJ" dcl_EAAD))  (exit))
    (action_tile "OATKZS_ZNH_QJINSERT" "(OATKZS_ZNH_QJRDDCL) (done_dialog 1)  (unload_dialog dcl_EAAD)")
    (action_tile "cancel" "(done_dialog 0)  (unload_dialog dcl_EAAD)")
    (setq dd (start_dialog))
    (if (= dd 1) (OATKZS_ZNHQJINSERT))
)




;|*****************************************************************************
工程设计OA图纸图框助手:智能化全局(读DCL数据）
20200410
|;
;;*****************************************************************************
(DEFUN OATKZS_ZNH_QJRDDCL () 
        (setq a11 (get_tile "OATKZS_ZNH_SJSM"))
        (setq a12 (get_tile "OATKZS_ZNH_XTKT"))
        (setq a13 (get_tile "OATKZS_ZNH_PDXTT"))
        (setq a21 (get_tile "OATKZS_ZNH_SBKZBZT"))
        (setq a22 (get_tile "OATKZS_ZNH_HJJKBZT"))
        (setq a23 (get_tile "OATKZS_ZNH_SBCLHZB"))
        (setq gzw_name (get_tile "OATKZS_ZNH_NAME"))
)

;|*****************************************************************************
工程设计OA图纸图框助手:智能化全局设计（图框插入）
20200410
|;
;;*****************************************************************************
(DEFUN OATKZS_ZNHQJINSERT (/ p OA_osm ) 
        (setq OA_osm (getvar "OSMODE"))
        (setvar "OSMODE" 0)
        (setq p (getpoint "\n图框插入点："))
        (if (= a11 "1")  (progn
              (command "insert"  MEAAD_CRTKNAME p meaad_all_scale meaad_all_scale 0  "explode" "L")
              (OAPUT_oneatt (entlast) "图名" (strcat gzw_name "智能化设计说明"))
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" (strcat gzw_name "智能化系统框图"))
              (OAPUT_oneatt (entlast) "图号" "SDQ9999-999")
              (setq p (polar p (dtr 270) (* 600 meaad_all_scale)))
        ))
        (if (= a13 "1")  (progn
              (command "insert"  MEAAD_CRTKNAME p meaad_all_scale meaad_all_scale 0  "explode" "L")
              (OAPUT_oneatt (entlast) "图名" (strcat gzw_name "智能化系统配电系统图"))
              (OAPUT_oneatt (entlast) "图号" "SDQ9999-999")
              (setq p (polar p (dtr 270) (* 600 meaad_all_scale)))
        ))
        (if (= a21 "1")  (progn
              (command "insert"  MEAAD_CRTKNAME p meaad_all_scale meaad_all_scale 0  "explode" "L")
              (OAPUT_oneatt (entlast) "图名" (strcat gzw_name "设备控制及仪表检测布置图"))
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0  "explode" "L")
              (OAPUT_oneatt (entlast) "图名" (strcat gzw_name "环境监控布置图"))
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" (strcat gzw_name "设备材料汇总表"))
              (OAPUT_oneatt (entlast) "图号" "SDQ9999-999")
              (setq p (polar p (dtr 270) (* 600 meaad_all_scale)))
        ))
       (setvar "OSMODE" OA_osm)
)



;|*****************************************************************************
工程设计OA图纸图框助手:设备控制设计对话框DCL主程序
20200410
|;
;;*****************************************************************************
(DEFUN DHK_TZTKZKSBKZ (/ dcl_EAAD a11 a12 a13 a21 a22 a23 PLC_NUM KZT_NUM dd) 
    (setq dcl_EAAD (load_dialog "Meaad_OATK_3.0.dcl"))
    (if (not  (new_dialog "MEAAD3_TZTK_ZNHSBKZ" dcl_EAAD))  (exit))
    (action_tile "OATKZS_ZNH_ZKINSERT" "(DHK_TZTK_ZNHZKRDDCL) (done_dialog 1)  (unload_dialog dcl_EAAD)")
    (action_tile "cancel" "(done_dialog 0)  (unload_dialog dcl_EAAD)")
    (setq dd (start_dialog))
    (if (= dd 1) (DHK_TZTKZNHZKINSERT))
)


;|*****************************************************************************
工程设计OA图纸图框助手:设备控制设计(读DCL数据）
20200410
|;
;;*****************************************************************************
(DEFUN DHK_TZTK_ZNHZKRDDCL () 
        (setq a11 (get_tile "OATKZS_ZNH_PLCIOHZB"))
        (setq a12 (get_tile "OATKZS_ZNH_PLCZKYQ"))
        (setq a13 (get_tile "OATKZS_ZNH_ZNKZT"))
        (setq a21 (get_tile "OATKZS_ZNH_PLCGTSJ"))
        (setq a22 (get_tile "OATKZS_ZNH_ZKSSJYQ"))
        (setq a23 (get_tile "OATKZS_ZNH_ZKSBCLTJB"))
        (setq PLC_NUM (get_tile "OATKZS_ZNH_PLCNUM"))
        (setq KZT_NUM (get_tile "OATKZS_ZNH_KZTNUM"))

)

;|*****************************************************************************
工程设计OA图纸图框助手:设备控制设计（图框插入）
20200413
|;
;;*****************************************************************************
(DEFUN DHK_TZTKZNHZKINSERT (/ p OA_osm ) 
        (setq OA_osm (getvar "OSMODE"))
        (setvar "OSMODE" 0)
        (setq p (getpoint "\n图框插入点："))
        (setq i 1)
        (setq PLC_num (atoi PLC_num))
        (setq KZT_NUM (atoi KZT_num))
        (if (= a11 "1") (progn
              (repeat PLC_num 
                       (command "insert"  MEAAD_CRTKNAME p meaad_all_scale meaad_all_scale 0  "explode" "L")
                       (OAPUT_oneatt (entlast) "图名" (strcat "PLC" (itoa i) "分站外部I/O接口一览表"))
                       (OAPUT_oneatt (entlast) "图号" "SDQ9999-999")
                       (setq p (polar p (dtr 270) (* 600 meaad_all_scale)))
                       (command "insert"  MEAAD_CRTKNAME p meaad_all_scale meaad_all_scale 0  "explode" "L")
                       (OAPUT_oneatt (entlast) "图名" (strcat "PLC" (itoa i) "分站外部I/O接口接线端子图"))
                       (OAPUT_oneatt (entlast) "图号" "SDQ9999-999")
                       (setq p (polar p (dtr 270) (* 600 meaad_all_scale)))
                       (setq i (+ 1 i))
              )
             (setq i 1)
        ))
        (if (= a12 "1")  (progn
              (command "insert"  MEAAD_CRTKNAME p meaad_all_scale meaad_all_scale 0  "explode" "L")
              (OAPUT_oneatt (entlast) "图名" "全厂设备自控要求一览表")
              (OAPUT_oneatt (entlast) "图号" "SDQ9999-999")
              (setq p (polar p (dtr 270) (* 600 meaad_all_scale)))
        ))
        (if (= a13 "1")  (progn
              (repeat KZT_num
                  (command "insert"  MEAAD_CRTKNAME p meaad_all_scale meaad_all_scale 0  "explode" "L")
                  (OAPUT_oneatt (entlast) "图名" "智能控制台设计图")
                  (OAPUT_oneatt (entlast) "图号" "SDQ9999-999")
                  (setq p (polar p (dtr 270) (* 600 meaad_all_scale)))
                  (setq i (+ 1 i))
              )
        ))
        (if (= a21 "1")  (progn
              (command "insert"  MEAAD_CRTKNAME p meaad_all_scale meaad_all_scale 0  "explode" "L")
              (OAPUT_oneatt (entlast) "图名" "PLC柜体要求图")
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0  "explode" "L")
              (OAPUT_oneatt (entlast) "图名" "中控室布置及要求图")
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" "自控系统设备材料统计表")
              (OAPUT_oneatt (entlast) "图号" "SDQ9999-999")
              (setq p (polar p (dtr 270) (* 600 meaad_all_scale)))
        ))
       (setvar "OSMODE" OA_osm)
)




;|*****************************************************************************
工程设计OA图纸图框助手:智能化仪表检测设计对话框DCL主程序
20200410
|;
;;*****************************************************************************
(DEFUN DHK_TZTKZKYBJC (/ dcl_EAAD a11 a12 a13 a21 a22 a23 gzw_name dd) 
    (setq dcl_EAAD (load_dialog "Meaad_OATK_3.0.dcl"))
    (if (not  (new_dialog "MEAAD3_TZTK_ZNHYBJC" dcl_EAAD))  (exit))
    (set_tile "OATKZS_ZNH_YBJCNAME" "工艺流程")
    (action_tile "OATKZS_ZNH_YBJCINSERT" "(DHK_TZTK_ZNHYBRDDCL) (done_dialog 1)  (unload_dialog dcl_EAAD)")
    (action_tile "cancel" "(done_dialog 0)  (unload_dialog dcl_EAAD)")
    (setq dd (start_dialog))
    (if (= dd 1) (DHK_TZTKZNHYBINSERT))
)


;|*****************************************************************************
工程设计OA图纸图框助手:智能化仪表检测设计(读DCL数据）
20200410
|;
;;*****************************************************************************
(DEFUN DHK_TZTK_ZNHYBRDDCL () 
        (setq a11 (get_tile "OATKZS_ZNH_YBJCPZT"))
        (setq a12 (get_tile "OATKZS_ZNH_YBJCYLB"))
        (setq a13 (get_tile "OATKZS_ZNH_YBDLPZB"))
        (setq a21 (get_tile "OATKZS_ZNH_JCYBJXT"))
        (setq a22 (get_tile "OATKZS_ZNH_JCYBAZT"))
        (setq a23 (get_tile "OATKZS_ZNH_YBSBCLB"))
        (setq gzw_name (get_tile "OATKZS_ZNH_YBJCNAME"))

)

;|*****************************************************************************
工程设计OA图纸图框助手:智能化仪表检测设计（图框插入）
20200413
|;
;;*****************************************************************************
(DEFUN DHK_TZTKZNHYBINSERT (/ p OA_osm ) 
        (setq OA_osm (getvar "OSMODE"))
        (setvar "OSMODE" 0)
        (setq p (getpoint "\n图框插入点："))
        (if (= a11 "1")  (progn
              (command "insert"  MEAAD_CRTKNAME p meaad_all_scale meaad_all_scale 0  "explode" "L")
              (OAPUT_oneatt (entlast) "图名" (strcat gzw_name "检测仪表配置图"))
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" (strcat gzw_name "检测仪表配置一览表"))
              (OAPUT_oneatt (entlast) "图号" "SDQ9999-999")
              (setq p (polar p (dtr 270) (* 600 meaad_all_scale)))
        ))
        (if (= a13 "1")  (progn
              (command "insert"  MEAAD_CRTKNAME p meaad_all_scale meaad_all_scale 0  "explode" "L")
              (OAPUT_oneatt (entlast) "图名" (strcat gzw_name "检测仪表电缆配置表"))
              (OAPUT_oneatt (entlast) "图号" "SDQ9999-999")
              (setq p (polar p (dtr 270) (* 600 meaad_all_scale)))
        ))
        (if (= a21 "1")  (progn
              (command "insert"  MEAAD_CRTKNAME p meaad_all_scale meaad_all_scale 0  "explode" "L")
              (OAPUT_oneatt (entlast) "图名" (strcat gzw_name "检测仪表接线参考图"))
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0  "explode" "L")
              (OAPUT_oneatt (entlast) "图名" (strcat gzw_name "检测仪表安装示意图"))
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" (strcat gzw_name "检测仪表设备材料表"))
              (OAPUT_oneatt (entlast) "图号" "SDQ9999-999")
              (setq p (polar p (dtr 270) (* 600 meaad_all_scale)))
        ))
       (setvar "OSMODE" OA_osm)
)

;|*****************************************************************************
工程设计OA图纸图框助手:智能化环境监控设计对话框DCL主程序
20200410
|;
;;*****************************************************************************
(DEFUN DHK_TZTKZKHJJK (/ dcl_EAAD a11 a12 a13 a14 a21 a22 a23 a24 gzw_name dd) 
    (setq dcl_EAAD (load_dialog "Meaad_OATK_3.0.dcl"))
    (if (not  (new_dialog "MEAAD3_TZTK_ZNHHJJK" dcl_EAAD))  (exit))
    (set_tile "OATKZS_ZNH_HJXTNAME" "")
    (action_tile "OATKZS_ZNH_HJXTINSERT" "(DHK_TZTK_ZNHHJRDDCL) (done_dialog 1)  (unload_dialog dcl_EAAD)")
    (action_tile "cancel" "(done_dialog 0)  (unload_dialog dcl_EAAD)")
    (setq dd (start_dialog))
    (if (= dd 1) (DHK_TZTKZNHHJINSERT))
)


;|*****************************************************************************
工程设计OA图纸图框助手:智能化环境监控设计(读DCL数据）
20200410
|;
;;*****************************************************************************
(DEFUN DHK_TZTK_ZNHHJRDDCL () 
        (setq a11 (get_tile "OATKZS_ZNH_HJJKXTT"))
        (setq a12 (get_tile "OATKZS_ZNH_QTJCXTT"))
        (setq a13 (get_tile "OATKZS_ZNH_WSDJCXTT"))
        (setq a14 (get_tile "OATKZS_ZNH_TXGBXTT"))
        (setq a21 (get_tile "OATKZS_ZNH_JCGLXTT"))
        (setq a22 (get_tile "OATKZS_ZNH_XGDWXTT"))
        (setq a23 (get_tile "OATKZS_ZNH_HJXTDLB"))
        (setq a24 (get_tile "OATKZS_ZNH_HJXTSBCLB"))
        (setq gzw_name (get_tile "OATKZS_ZNH_HJXTNAME"))

)

;|*****************************************************************************
工程设计OA图纸图框助手:智能化环境监控设计（图框插入）
20200413
|;
;;*****************************************************************************
(DEFUN DHK_TZTKZNHHJINSERT (/ p OA_osm ) 
        (setq OA_osm (getvar "OSMODE"))
        (setvar "OSMODE" 0)
        (setq p (getpoint "\n图框插入点："))
        (if (= a11 "1")  (progn
              (command "insert"  MEAAD_CRTKNAME p meaad_all_scale meaad_all_scale 0  "explode" "L")
              (OAPUT_oneatt (entlast) "图名" (strcat gzw_name "环境监控各单项系统图"))
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" (strcat gzw_name "气体及温湿度检测系统图"))
              (OAPUT_oneatt (entlast) "图号" "SDQ9999-999")
              (setq p (polar p (dtr 270) (* 600 meaad_all_scale)))
        ))
        (if (= a13 "1")  (progn
              (command "insert"  MEAAD_CRTKNAME p meaad_all_scale meaad_all_scale 0  "explode" "L")
              (OAPUT_oneatt (entlast) "图名" (strcat gzw_name "视频监控系统图"))
              (OAPUT_oneatt (entlast) "图号" "SDQ9999-999")
              (setq p (polar p (dtr 270) (* 600 meaad_all_scale)))
        ))
        (if (= a14 "1")  (progn
              (command "insert"  MEAAD_CRTKNAME p meaad_all_scale meaad_all_scale 0  "explode" "L")
              (OAPUT_oneatt (entlast) "图名" (strcat gzw_name "通讯及广播系统图"))
              (OAPUT_oneatt (entlast) "图号" "SDQ9999-999")
              (setq p (polar p (dtr 270) (* 600 meaad_all_scale)))
        ))
        (if (= a21 "1")  (progn
              (command "insert"  MEAAD_CRTKNAME p meaad_all_scale meaad_all_scale 0  "explode" "L")
              (OAPUT_oneatt (entlast) "图名" (strcat gzw_name "进出口管理安防系统图"))
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0  "explode" "L")
              (OAPUT_oneatt (entlast) "图名" (strcat gzw_name "厂区巡更和定位系统图"))
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" (strcat gzw_name "环境监控系统电缆配置表"))
              (OAPUT_oneatt (entlast) "图号" "SDQ9999-999")
              (setq p (polar p (dtr 270) (* 600 meaad_all_scale)))
        ))
        (if (= a24 "1")  (progn
              (command "insert"  MEAAD_CRTKNAME p meaad_all_scale meaad_all_scale 0  "explode" "L")
              (OAPUT_oneatt (entlast) "图名" (strcat gzw_name "环境监控系统设备材料表"))
              (OAPUT_oneatt (entlast) "图号" "SDQ9999-999")
              (setq p (polar p (dtr 270) (* 600 meaad_all_scale)))
        ))
       (setvar "OSMODE" OA_osm)
)


;|*****************************************************************************
工程设计OA图纸图框助手:智能化布置图设计对话框DCL主程序
20200410
|;
;;*****************************************************************************
(DEFUN DHK_TZTKZKBZT (/ dcl_EAAD a11 a12 gzw_name dd) 
    (setq dcl_EAAD (load_dialog "Meaad_OATK_3.0.dcl"))
    (DHK_TZTK_ZNHDAORU)
    (if (not  (new_dialog "MEAAD3_TZTK_ZNHBZT" dcl_EAAD))  (exit))
    (set_tile "OATKZS_ZNH_GZWNAME" GZWDTNAME)
    (action_tile "OATKZS_ZNH_BZTINSERT" "(DHK_TZTK_ZNHBZTRDDCL) (done_dialog 1)  (unload_dialog dcl_EAAD)")
    (action_tile "cancel" "(done_dialog 0)  (unload_dialog dcl_EAAD)")
    (setq dd (start_dialog))
    (cond ((= dd 1) (OATKZS_ZNHBZTINSERT))
    )
)


;|*****************************************************************************
工程设计OA图纸图框助手:智能化布置图设计--单体构筑物名称导入
20200413
|;
;;*****************************************************************************
(DEFUN DHK_TZTK_ZNHDAORU (/ OA_osm ss SUM_n i en0 vn0 )
    (setq OA_osm (getvar "OSMODE"))
    (setvar "OSMODE" 0)
    (if  (= Meaad_all_scale nil) (setq meaad_all_scale (getint "\n出图比例因数Meaad_all_scale还没有定义，请输入1：<1,100,200,1000>："))) 
    (if  (= Meaad_all_scale nil) (setq meaad_all_scale 1))
    (print "\n从工程总目录上选择单体构筑物名称（Text类型，顺序从上倒下):")
    (setq SS (ssget '((0 . "TEXT")))) 
    (setq SUM_n (sslength ss))
    (setq SS  (SORT-SE SS 10 1 (* Meaad_all_scale 4) T))
    (setq i 0)
    (setq GZWDTNAME "")
    (repeat SUM_n
       (setq en0 (ssname ss i))
       (setq vn0 (vlax-ename->vla-object en0))
       (setq dan (vla-get-TextString vn0))
       (setq GZWDTNAME (strcat GZWDTNAME dan ";"))
       (setq i (+ 1 i))
    )
    (setq GZWDTNAME (substr GZWDTNAME 1 (- (strlen GZWDTNAME) 1)))
    (print GZWDTNAME)
    (setvar "OSMODE" OA_osm)
)


;|*****************************************************************************
工程设计OA图纸图框助手:智能化布置图设计(读DCL数据）
20200410
|;
;;*****************************************************************************
(DEFUN DHK_TZTK_ZNHBZTRDDCL () 
        (setq a11 (get_tile "OATKZS_ZNH_YBZKBZT"))
        (setq a12 (get_tile "OATKZS_ZNH_HJJKBZT"))
        (setq gzw_name (get_tile "OATKZS_ZNH_GZWNAME"))
)

;|*****************************************************************************
工程设计OA图纸图框助手:智能化布置图设计（图框插入）
20200413
|;
;;*****************************************************************************
(DEFUN OATKZS_ZNHBZTINSERT (/ p OA_osm PJ-sxz i) 
   (setq OA_osm (getvar "OSMODE"))
   (setvar "OSMODE" 0)
   (if  (= Meaad_all_scale nil) (setq meaad_all_scale (getint "\n出图比例因数Meaad_all_scale还没有定义，请输入1：<1,100,200,1000>："))) 
    (if  (= Meaad_all_scale nil) (setq meaad_all_scale 1))
   (setq p (getpoint "\n图框插入点："))
   (setq PJ-sxz (parse7 gzw_name ";"))
   (setq i 0)
   (while  (/= (setq gzw_name (nth i PJ-sxz)) nil)
        (if (= a11 "1")  (progn
              (command "insert"  MEAAD_CRTKNAME p meaad_all_scale meaad_all_scale 0  "explode" "L")
              (OAPUT_oneatt (entlast) "图名" (strcat gzw_name "仪表及自控设备布置图"))
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" (strcat gzw_name "环境监控设备布置图"))
              (OAPUT_oneatt (entlast) "图号" "SDQ9999-999")
              (setq p (polar p (dtr 270) (* 600 meaad_all_scale)))
        ))
        (setq i (+ 1 i))
    )  
   (setvar "OSMODE" OA_osm)
)

;|*****************************************************************************
工程设计OA图纸图框助手:初步设计对话框DCL主程序
20200410
|;
;;*****************************************************************************
(DEFUN DHK_TZTKCBSJ (/ dcl_EAAD a11 a12 a13 a14 a15 a16 a21 a22 a23 a24 A25 a26 
a31 a32 a33 a34 a35 a36 gzw_name dd) 
    (setq dcl_EAAD (load_dialog "Meaad_OATK_3.0.dcl"))
    (if (not  (new_dialog "MEAAD3_TZTK_CBSJ" dcl_EAAD))  (exit))
    (set_tile "OATKZS_CBSJ_QIANZHUI" "")
    (action_tile "OATKZS_CBSJ_CSINSERT" "(DHK_TZTK_CBSJRDDCL) (done_dialog 1)  (unload_dialog dcl_EAAD)")
    (action_tile "cancel" "(done_dialog 0)  (unload_dialog dcl_EAAD)")
    (setq dd (start_dialog))
    (if (= dd 1) (DHK_TZTKCBSJINSERT))
)


;|*****************************************************************************
工程设计OA图纸图框助手:初步设计(读DCL数据）
20200410
|;
;;*****************************************************************************
(DEFUN DHK_TZTK_CBSJRDDCL () 
        (setq a11 (get_tile "OATKZS_CBSJ_DHSBB"))
        (setq a12 (get_tile "OATKZS_CBSJ_HVPDXT"))
        (setq a13 (get_tile "OATKZS_CBSJ_DLJKXT"))
        (setq a14 (get_tile "OATKZS_CBSJ_LVPDXT"))
        (setq a15 (get_tile "OATKZS_CBSJ_EPS"))
        (setq a16 (get_tile "OATKZS_CBSJ_ZNZM"))
        (setq a21 (get_tile "OATKZS_CBSJ_PDJBZT"))
        (setq a22 (get_tile "OATKZS_CBSJ_ZNHXTT"))
        (setq a23 (get_tile "OATKZS_CBSJ_ZYZKKT"))
        (setq a24 (get_tile "OATKZS_CBSJ_YBJCXT"))
        (setq a25 (get_tile "OATKZS_CBSJ_ZNHXT"))
        (setq a26 (get_tile "OATKZS_CBSJ_JTJCXT"))
        (setq a31 (get_tile "OATKZS_CBSJ_WSDJCXT"))
        (setq a32 (get_tile "OATKZS_CBSJ_SPJKXT"))
        (setq a33 (get_tile "OATKZS_CBSJ_TXGBXT"))
        (setq a34 (get_tile "OATKZS_CBSJ_JCAFXT"))
        (setq a35 (get_tile "OATKZS_CBSJ_XGDWXT"))
        (setq a36 (get_tile "OATKZS_CBSJ_DLZKBZ"))
        (setq gzw_name (get_tile "OATKZS_CBSJ_QIANZHUI"))
)

;|*****************************************************************************
工程设计OA图纸图框助手:初步设计（图框插入）
20200413
|;
;;*****************************************************************************
(DEFUN DHK_TZTKCBSJINSERT (/ p OA_osm ) 
        (setq OA_osm (getvar "OSMODE"))
        (setvar "OSMODE" 0)
        (setq p (getpoint "\n图框插入点："))
        (if (= a11 "1")  (progn
              (command "insert"  MEAAD_CRTKNAME p meaad_all_scale meaad_all_scale 0  "explode" "L")
              (OAPUT_oneatt (entlast) "图名" (strcat gzw_name "项目代号及主要设备材料表"))
              (OAPUT_oneatt (entlast) "图号" "SDQ9999-999")
              (setq p (polar p (dtr 270) (* 600 meaad_all_scale)))
        ))
        (if (= a12 "1")  (progn
              (command "insert"  MEAAD_CRTKNAME p meaad_all_scale meaad_all_scale 0  "explode" "L")
              (OAPUT_oneatt (entlast) "图名" (strcat gzw_name "高压配电系统图"))
              (OAPUT_oneatt (entlast) "图号" "SDQ9999-999")
              (setq p (polar p (dtr 270) (* 600 meaad_all_scale)))
        ))
        (if (= a13 "1")  (progn
              (command "insert"  MEAAD_CRTKNAME p meaad_all_scale meaad_all_scale 0  "explode" "L")
              (OAPUT_oneatt (entlast) "图名" (strcat gzw_name "电力监控系统图"))
              (OAPUT_oneatt (entlast) "图号" "SDQ9999-999")
              (setq p (polar p (dtr 270) (* 600 meaad_all_scale)))
        ))
        (if (= a14 "1")  (progn
              (command "insert"  MEAAD_CRTKNAME p meaad_all_scale meaad_all_scale 0  "explode" "L")
              (OAPUT_oneatt (entlast) "图名" (strcat gzw_name "低压配电系统图"))
              (OAPUT_oneatt (entlast) "图号" "SDQ9999-999")
              (setq p (polar p (dtr 270) (* 600 meaad_all_scale)))
        ))
        (if (= a15 "1")  (progn
              (command "insert"  MEAAD_CRTKNAME p meaad_all_scale meaad_all_scale 0  "explode" "L")
              (OAPUT_oneatt (entlast) "图名" (strcat gzw_name "EPS应急电源配电系统图"))
              (OAPUT_oneatt (entlast) "图号" "SDQ9999-999")
              (setq p (polar p (dtr 270) (* 600 meaad_all_scale)))
        ))
        (if (= a16 "1")  (progn
              (command "insert"  MEAAD_CRTKNAME p meaad_all_scale meaad_all_scale 0  "explode" "L")
              (OAPUT_oneatt (entlast) "图名" (strcat gzw_name "智能照明系统图"))
              (OAPUT_oneatt (entlast) "图号" "SDQ9999-999")
              (setq p (polar p (dtr 270) (* 600 meaad_all_scale)))
        ))

        (if (= a21 "1")  (progn
              (command "insert"  MEAAD_CRTKNAME p meaad_all_scale meaad_all_scale 0  "explode" "L")
              (OAPUT_oneatt (entlast) "图名" (strcat gzw_name "配电间动力布置图"))
              (OAPUT_oneatt (entlast) "图号" "SDQ9999-999")
              (setq p (polar p (dtr 270) (* 600 meaad_all_scale)))
        ))
        (if (= a22 "1")  (progn
              (command "insert"  MEAAD_CRTKNAME p meaad_all_scale meaad_all_scale 0  "explode" "L")
              (OAPUT_oneatt (entlast) "图名" (strcat gzw_name "智能化系统框图"))
              (OAPUT_oneatt (entlast) "图号" "SDQ9999-999")
              (setq p (polar p (dtr 270) (* 600 meaad_all_scale)))
        ))
        (if (= a23 "1")  (progn
              (command "insert"  MEAAD_CRTKNAME p meaad_all_scale meaad_all_scale 0  "explode" "L")
              (OAPUT_oneatt (entlast) "图名" (strcat gzw_name "主要自控项目系统框图"))
              (OAPUT_oneatt (entlast) "图号" "SDQ9999-999")
              (setq p (polar p (dtr 270) (* 600 meaad_all_scale)))
        ))
        (if (= a24 "1")  (progn
              (command "insert"  MEAAD_CRTKNAME p meaad_all_scale meaad_all_scale 0  "explode" "L")
              (OAPUT_oneatt (entlast) "图名" (strcat gzw_name "工艺参数检测仪表配置图"))
              (OAPUT_oneatt (entlast) "图号" "SDQ9999-999")
              (setq p (polar p (dtr 270) (* 600 meaad_all_scale)))
        ))
        (if (= a25 "1")  (progn
              (command "insert"  MEAAD_CRTKNAME p meaad_all_scale meaad_all_scale 0  "explode" "L")
              (OAPUT_oneatt (entlast) "图名" (strcat gzw_name "环境监控各单项系统图"))
              (OAPUT_oneatt (entlast) "图号" "SDQ9999-999")
              (setq p (polar p (dtr 270) (* 600 meaad_all_scale)))
        ))
        (if (= a26 "1")  (progn
              (command "insert"  MEAAD_CRTKNAME p meaad_all_scale meaad_all_scale 0  "explode" "L")
              (OAPUT_oneatt (entlast) "图名" (strcat gzw_name "气体检测系统图"))
              (OAPUT_oneatt (entlast) "图号" "SDQ9999-999")
              (setq p (polar p (dtr 270) (* 600 meaad_all_scale)))
        ))
        (if (= a31 "1")  (progn
              (command "insert"  MEAAD_CRTKNAME p meaad_all_scale meaad_all_scale 0  "explode" "L")
              (OAPUT_oneatt (entlast) "图名" (strcat gzw_name "温湿度检测系统图"))
              (OAPUT_oneatt (entlast) "图号" "SDQ9999-999")
              (setq p (polar p (dtr 270) (* 600 meaad_all_scale)))
        ))
        (if (= a32 "1")  (progn
              (command "insert"  MEAAD_CRTKNAME p meaad_all_scale meaad_all_scale 0  "explode" "L")
              (OAPUT_oneatt (entlast) "图名" (strcat gzw_name "视频监控系统图"))
              (OAPUT_oneatt (entlast) "图号" "SDQ9999-999")
              (setq p (polar p (dtr 270) (* 600 meaad_all_scale)))
        ))
        (if (= a33 "1")  (progn
              (command "insert"  MEAAD_CRTKNAME p meaad_all_scale meaad_all_scale 0  "explode" "L")
              (OAPUT_oneatt (entlast) "图名" (strcat gzw_name "通讯及广播系统图"))
              (OAPUT_oneatt (entlast) "图号" "SDQ9999-999")
              (setq p (polar p (dtr 270) (* 600 meaad_all_scale)))
        ))
        (if (= a34 "1")  (progn
              (command "insert"  MEAAD_CRTKNAME p meaad_all_scale meaad_all_scale 0  "explode" "L")
              (OAPUT_oneatt (entlast) "图名" (strcat gzw_name "进出口管理安防系统图"))
              (OAPUT_oneatt (entlast) "图号" "SDQ9999-999")
              (setq p (polar p (dtr 270) (* 600 meaad_all_scale)))
        ))
        (if (= a35 "1")  (progn
              (command "insert"  MEAAD_CRTKNAME p meaad_all_scale meaad_all_scale 0  "explode" "L")
              (OAPUT_oneatt (entlast) "图名" (strcat gzw_name "厂区巡更和定位系统图"))
              (OAPUT_oneatt (entlast) "图号" "SDQ9999-999")
              (setq p (polar p (dtr 270) (* 600 meaad_all_scale)))
        ))
        (if (= a36 "1")  (progn
              (command "insert"  MEAAD_CRTKNAME p meaad_all_scale meaad_all_scale 0  "explode" "L")
              (OAPUT_oneatt (entlast) "图名" (strcat gzw_name "动力及智能化布置图"))
              (OAPUT_oneatt (entlast) "图号" "SDQ9999-999")
              (setq p (polar p (dtr 270) (* 600 meaad_all_scale)))
        ))
       (setvar "OSMODE" OA_osm)
)


;|*****************************************************************************
OA图框工具：用以贱人工具箱PDF批量打印的贵人绘图框
--全局系统变量如下：
    Meaad_all_Scale            全局比例因子 
|;
;;*****************************************************************************
(defun DHK_OAJRCTFZ(/ p1 xbl ybl OA_osm ss ss_len en0 vn0 i TKBLK_name kd)
  (setq kd (getint"\n选择操作类型  1-加贵人出图框  2-删贵人出图框 3-多信息图名更换"))
  (cond ((= kd 1) 
      (setq OA_osm (getvar "OSMODE"))
      (setvar "OSMODE" 0)
      (if  (= Meaad_all_scale nil) (setq meaad_all_scale (getint "\n出图比例因数Meaad_all_scale还没有定义，请输入1：<1,100,200,1000>：")))
    (if  (= Meaad_all_scale nil) (setq meaad_all_scale 1))
      (princ "\n选取要绘图的全部图纸...")
      (while  (setq ss (ssget  '((0 . "INSERT") (2 . "*图框_A*框*"))))
            (setq ss (SORT-SE (SORT-SE ss 10 0 (* 150 Meaad_all_scale) nil) 10 1 (* 150 Meaad_all_scale) T))
            (setq ss_len (sslength ss))
            (setq i 0)
            (while (< i ss_len)
               (setq en0 (ssname ss i))
               (setq vn0 (vlax-ename->vla-object en0))
               (setq TKBLK_name (vla-get-name vn0))
               (setq P1 (oaget_blkpoint en0))               
               (cond ((wcmatch TKBLK_name "*图框_A3_420_横*") 
                             (setq xbl (*  Meaad_all_Scale 420))
                             (setq ybl (*  Meaad_all_Scale 297))
                      )
                      ((wcmatch TKBLK_name "*图框_A3加_472_横*") 
                             (setq xbl (*  Meaad_all_Scale 472))
                             (setq ybl (*  Meaad_all_Scale 297))
                      )
                      ((wcmatch TKBLK_name "*图框_A3加_525_横*") 
                             (setq xbl (*  Meaad_all_Scale 525))
                             (setq ybl (*  Meaad_all_Scale 297))
                      )
                      ((wcmatch TKBLK_name "*图框_A3加_630_横*") 
                             (setq xbl (*  Meaad_all_Scale 630))
                             (setq ybl (*  Meaad_all_Scale 297))
                      )
                      ((wcmatch TKBLK_name "*图框_A3加_735_横*") 
                             (setq xbl (*  Meaad_all_Scale 735))
                             (setq ybl (*  Meaad_all_Scale 297))
                      )
                      ((wcmatch TKBLK_name "*图框_A3加_840_横*") 
                             (setq xbl (*  Meaad_all_Scale 840))
                             (setq ybl (*  Meaad_all_Scale 297))
                      )
                      ((wcmatch TKBLK_name "*图框_A2_594_横*") 
                             (setq xbl (*  Meaad_all_Scale 594))
                             (setq ybl (*  Meaad_all_Scale 420))
                      )
                      ((wcmatch TKBLK_name "*图框_A2加_668_横*") 
                             (setq xbl (*  Meaad_all_Scale 668))
                             (setq ybl (*  Meaad_all_Scale 420))
                      )
                      ((wcmatch TKBLK_name "*图框_A2加_742_横*") 
                             (setq xbl (*  Meaad_all_Scale 742))
                             (setq ybl (*  Meaad_all_Scale 420))
                      )
                      ((wcmatch TKBLK_name "*图框_A2加_891_横*") 
                             (setq xbl (*  Meaad_all_Scale 891))
                             (setq ybl (*  Meaad_all_Scale 420))
                      )
                      ((wcmatch TKBLK_name "*图框_A2加_1039_横*") 
                             (setq xbl (*  Meaad_all_Scale 1039))
                             (setq ybl (*  Meaad_all_Scale 420))
                      )
                      ((wcmatch TKBLK_name "*图框_A2加_1188_横*") 
                             (setq xbl (*  Meaad_all_Scale 1188))
                             (setq ybl (*  Meaad_all_Scale 420))
                      )
                      ((wcmatch TKBLK_name "*图框_A1_841_横*") 
                             (setq xbl (*  Meaad_all_Scale 841))
                             (setq ybl (*  Meaad_all_Scale 594))
                      )
                      ((wcmatch TKBLK_name "*图框_A1加_946_横*") 
                             (setq xbl (*  Meaad_all_Scale 946))
                             (setq ybl (*  Meaad_all_Scale 594))
                      )
                      ((wcmatch TKBLK_name "*图框_A1加_1051_横*") 
                             (setq xbl (*  Meaad_all_Scale 1051))
                             (setq ybl (*  Meaad_all_Scale 594))
                      )
                      ((wcmatch TKBLK_name "*图框_A1加_1261_横*") 
                             (setq xbl (*  Meaad_all_Scale 1261))
                             (setq ybl (*  Meaad_all_Scale 594))
                      )
                      ((wcmatch TKBLK_name "*图框_A1加_1471_横*") 
                             (setq xbl (*  Meaad_all_Scale 1471))
                             (setq ybl (*  Meaad_all_Scale 594))
                      )
                      ((wcmatch TKBLK_name "*图框_A1加_1682_横*") 
                             (setq xbl (*  Meaad_all_Scale 1682))
                             (setq ybl (*  Meaad_all_Scale 594))
                      )
                      ((wcmatch TKBLK_name "*图框_A0_1189_横*") 
                             (setq xbl (*  Meaad_all_Scale 1189))
                             (setq ybl (*  Meaad_all_Scale 841))
                      )
                      ((wcmatch TKBLK_name "*图框_A0加_1337_横*") 
                             (setq xbl (*  Meaad_all_Scale 1337))
                             (setq ybl (*  Meaad_all_Scale 841))
                      )
                      ((wcmatch TKBLK_name "*图框_A0加_1486_横*") 
                             (setq xbl (*  Meaad_all_Scale 1486))
                             (setq ybl (*  Meaad_all_Scale 841))
                      )
                      ((wcmatch TKBLK_name "*图框_A0加_1783_横*") 
                             (setq xbl (*  Meaad_all_Scale 1783))
                             (setq ybl (*  Meaad_all_Scale 841))
                      )
                      ((wcmatch TKBLK_name "*图框_A0加_2080_横*") 
                             (setq xbl (*  Meaad_all_Scale 2080))
                             (setq ybl (*  Meaad_all_Scale 841))
                      )
                      ((wcmatch TKBLK_name "*图框_A0加_2378_横*") 
                             (setq xbl (*  Meaad_all_Scale 2378))
                             (setq ybl (*  Meaad_all_Scale 841))
                      )
                   )
(print TKBLK_name)
(print xbl)
(print ybl)
(print p1)
                  (command "insert" "OA绘图_贵人出图框" p1 xbl ybl 0)
                  (setq i (+ i 1))
               )
          )
         (setvar "OSMODE" OA_osm)
     )
    ((= kd 2)
       (setq OA_osm (getvar "OSMODE"))
       (setvar "OSMODE" 0)
       (princ "\n选取要删除贵人绘图框的范围...")
       (while (/= (setq ss (ssget  '((0 . "INSERT") (2 . "OA绘图_贵人出图框")))) nil)
         (command "erase" ss "")
         (princ "\n选取要删除贵人绘图框的范围...")
       )
    )
    ((= kd 3) (DHK_OADXXPDFGMZ))
  )
)


;|*****************************************************************************
OA图框工具：插删入签名块
--全局系统变量如下：
    Meaad_all_Scale            全局比例因子 
|;
;;*****************************************************************************
(defun DHK_NOOACRQM(/ p1 xbl ybl OA_osm ss ss_len en0 vn0 i p1 p2 p3 p4 TKBLK_name qmtk newqm QMBLK_name qmdel BLK_name)
  (setq kd (getint"\n选择操作类型  1-加签名图框  2-删签名图块"))
  (if (= kd 1) (progn
    (setq OA_osm (getvar "OSMODE"))
    (setvar "OSMODE" 0)
    (if  (= Meaad_all_scale nil) (setq meaad_all_scale (getint "\n出图比例因数Meaad_all_scale还没有定义，请输入1：<1,100,200,1000>：")))
    (if  (= Meaad_all_scale nil) (setq meaad_all_scale 1))
    (setq qmtk  (car (entsel  "\n选取签名图块（图框插入点应在图框右下角）："))) 
    (setq newqm (ssadd))
    (setq newqm (ssadd qmtk newqm)) ;要拷贝的标准图框选择集
    (setq oldppp (OAGET_BLKPOINT qmtk));标准图框块插入点
    (setq vn0 (vlax-ename->vla-object qmtk))
    (setq QMBLK_name (vla-get-name vn0))
    (princ "\n选取要插入签名块的全部图纸...")
    (while  (setq ss (ssget  '((0 . "INSERT") (2 . "*图框_A*框*"))))
            (setq ss (SORT-SE (SORT-SE ss 10 0 (* 150 Meaad_all_scale) nil) 10 1 (* 150 Meaad_all_scale) T))
            (setq ss_len (sslength ss))
            (setq i 0)
            (while (< i ss_len)
               (setq en0 (ssname ss i))
               (setq vn0 (vlax-ename->vla-object en0))
               (setq TKBLK_name (vla-get-name vn0))
               (setq P1 (oaget_blkpoint en0))  
               (cond ((wcmatch TKBLK_name "*图框_A3_420_横*") 
                             (setq p2 (polar p1 0 (*  Meaad_all_Scale 420)))
                             (setq p3 (polar p1 (dtr 90)  (*  Meaad_all_Scale 297)))
                             (setq p4 (polar p2 (dtr 90)  (*  Meaad_all_Scale 297)))
                      )
                      ((wcmatch TKBLK_name "*图框_A3加_472_横*") 
                             (setq p2 (polar p1 0 (*  Meaad_all_Scale 472)))
                             (setq p3 (polar p1 (dtr 90)  (*  Meaad_all_Scale 297)))
                             (setq p4 (polar p2 (dtr 90)  (*  Meaad_all_Scale 297)))
                      )
                      ((wcmatch TKBLK_name "*图框_A3加_525_横*") 
                             (setq p2 (polar p1 0 (*  Meaad_all_Scale 525)))
                             (setq p3 (polar p1 (dtr 90)  (*  Meaad_all_Scale 297)))
                             (setq p4 (polar p2 (dtr 90)  (*  Meaad_all_Scale 297)))
                      )
                      ((wcmatch TKBLK_name "*图框_A3加_630_横*") 
                             (setq p2 (polar p1 0 (*  Meaad_all_Scale 630)))
                             (setq p3 (polar p1 (dtr 90)  (*  Meaad_all_Scale 297)))
                             (setq p4 (polar p2 (dtr 90)  (*  Meaad_all_Scale 297)))
                      )
                      ((wcmatch TKBLK_name "*图框_A3加_735_横*") 
                             (setq p2 (polar p1 0 (*  Meaad_all_Scale 735)))
                             (setq p3 (polar p1 (dtr 90)  (*  Meaad_all_Scale 297)))
                             (setq p4 (polar p2 (dtr 90)  (*  Meaad_all_Scale 297)))
                      )
                      ((wcmatch TKBLK_name "*图框_A3加_840_横*") 
                             (setq p2 (polar p1 0 (*  Meaad_all_Scale 840)))
                             (setq p3 (polar p1 (dtr 90)  (*  Meaad_all_Scale 297)))
                             (setq p4 (polar p2 (dtr 90)  (*  Meaad_all_Scale 297)))
                      )
                      ((wcmatch TKBLK_name "*图框_A2_594_横*") 
                             (setq p2 (polar p1 0 (*  Meaad_all_Scale 594)))
                             (setq p3 (polar p1 (dtr 90)  (*  Meaad_all_Scale 420)))
                             (setq p4 (polar p2 (dtr 90)  (*  Meaad_all_Scale 420)))
                      )
                      ((wcmatch TKBLK_name "*图框_A2加_668_横*") 
                             (setq p2 (polar p1 0 (*  Meaad_all_Scale 668)))
                             (setq p3 (polar p1 (dtr 90)  (*  Meaad_all_Scale 420)))
                             (setq p4 (polar p2 (dtr 90)  (*  Meaad_all_Scale 420)))
                      )
                      ((wcmatch TKBLK_name "*图框_A2加_742_横*") 
                             (setq p2 (polar p1 0 (*  Meaad_all_Scale 742)))
                             (setq p3 (polar p1 (dtr 90)  (*  Meaad_all_Scale 420)))
                             (setq p4 (polar p2 (dtr 90)  (*  Meaad_all_Scale 420)))
                      )
                      ((wcmatch TKBLK_name "*图框_A2加_891_横*") 
                             (setq p2 (polar p1 0 (*  Meaad_all_Scale 891)))
                             (setq p3 (polar p1 (dtr 90)  (*  Meaad_all_Scale 420)))
                             (setq p4 (polar p2 (dtr 90)  (*  Meaad_all_Scale 420)))
                      )
                      ((wcmatch TKBLK_name "*图框_A2加_1039_横*") 
                             (setq p2 (polar p1 0 (*  Meaad_all_Scale 1039)))
                             (setq p3 (polar p1 (dtr 90)  (*  Meaad_all_Scale 420)))
                             (setq p4 (polar p2 (dtr 90)  (*  Meaad_all_Scale 420)))
                      )
                      ((wcmatch TKBLK_name "*图框_A2加_1188_横*") 
                             (setq p2 (polar p1 0 (*  Meaad_all_Scale 1188)))
                             (setq p3 (polar p1 (dtr 90)  (*  Meaad_all_Scale 420)))
                             (setq p4 (polar p2 (dtr 90)  (*  Meaad_all_Scale 420)))
                      )
                      ((wcmatch TKBLK_name "*图框_A1_841_横*") 
                             (setq p2 (polar p1 0 (*  Meaad_all_Scale 841)))
                             (setq p3 (polar p1 (dtr 90)  (*  Meaad_all_Scale 594)))
                             (setq p4 (polar p2 (dtr 90)  (*  Meaad_all_Scale 594)))
                      )
                      ((wcmatch TKBLK_name "*图框_A1加_946_横*") 
                             (setq p2 (polar p1 0 (*  Meaad_all_Scale 946)))
                             (setq p3 (polar p1 (dtr 90)  (*  Meaad_all_Scale 594)))
                             (setq p4 (polar p2 (dtr 90)  (*  Meaad_all_Scale 594)))
                      )
                      ((wcmatch TKBLK_name "*图框_A1加_1051_横*") 
                             (setq p2 (polar p1 0 (*  Meaad_all_Scale 1051)))
                             (setq p3 (polar p1 (dtr 90)  (*  Meaad_all_Scale 594)))
                             (setq p4 (polar p2 (dtr 90)  (*  Meaad_all_Scale 594)))
                      )
                      ((wcmatch TKBLK_name "*图框_A1加_1261_横*") 
                             (setq p2 (polar p1 0 (*  Meaad_all_Scale 1261)))
                             (setq p3 (polar p1 (dtr 90)  (*  Meaad_all_Scale 594)))
                             (setq p4 (polar p2 (dtr 90)  (*  Meaad_all_Scale 594)))
                      )
                      ((wcmatch TKBLK_name "*图框_A1加_1471_横*") 
                             (setq p2 (polar p1 0 (*  Meaad_all_Scale 1471)))
                             (setq p3 (polar p1 (dtr 90)  (*  Meaad_all_Scale 594)))
                             (setq p4 (polar p2 (dtr 90)  (*  Meaad_all_Scale 594)))
                      )
                      ((wcmatch TKBLK_name "*图框_A1加_1682_横*") 
                             (setq p2 (polar p1 0 (*  Meaad_all_Scale 1682)))
                             (setq p3 (polar p1 (dtr 90)  (*  Meaad_all_Scale 594)))
                             (setq p4 (polar p2 (dtr 90)  (*  Meaad_all_Scale 594)))
                      )
                      ((wcmatch TKBLK_name "*图框_A0_1189_横*") 
                             (setq p2 (polar p1 0 (*  Meaad_all_Scale 1189)))
                             (setq p3 (polar p1 (dtr 90)  (*  Meaad_all_Scale 841)))
                             (setq p4 (polar p2 (dtr 90)  (*  Meaad_all_Scale 841)))
                      )
                      ((wcmatch TKBLK_name "*图框_A0加_1337_横*") 
                             (setq p2 (polar p1 0 (*  Meaad_all_Scale 1337)))
                             (setq p3 (polar p1 (dtr 90)  (*  Meaad_all_Scale 841)))
                             (setq p4 (polar p2 (dtr 90)  (*  Meaad_all_Scale 841)))
                      )
                      ((wcmatch TKBLK_name "*图框_A0加_1486_横*") 
                             (setq p2 (polar p1 0 (*  Meaad_all_Scale 1486)))
                             (setq p3 (polar p1 (dtr 90)  (*  Meaad_all_Scale 841)))
                             (setq p4 (polar p2 (dtr 90)  (*  Meaad_all_Scale 841)))
                      )
                      ((wcmatch TKBLK_name "*图框_A0加_1783_横*") 
                             (setq p2 (polar p1 0 (*  Meaad_all_Scale 1783)))
                             (setq p3 (polar p1 (dtr 90)  (*  Meaad_all_Scale 841)))
                             (setq p4 (polar p2 (dtr 90)  (*  Meaad_all_Scale 841)))
                      )
                      ((wcmatch TKBLK_name "*图框_A0加_2080_横*") 
                             (setq p2 (polar p1 0 (*  Meaad_all_Scale 2080)))
                             (setq p3 (polar p1 (dtr 90)  (*  Meaad_all_Scale 841)))
                             (setq p4 (polar p2 (dtr 90)  (*  Meaad_all_Scale 841)))
                      )
                      ((wcmatch TKBLK_name "*图框_A0加_2378_横*") 
                             (setq p2 (polar p1 0 (*  Meaad_all_Scale 2378)))
                             (setq p3 (polar p1 (dtr 90)  (*  Meaad_all_Scale 841)))
                             (setq p4 (polar p2 (dtr 90)  (*  Meaad_all_Scale 841)))
                      )
                   )
                  (command "insert" QMBLK_name p2 Meaad_all_Scale Meaad_all_Scale 0)
                  (setq i (+ i 1))
               )
         )
       (setvar "OSMODE" OA_osm)   
    )
   (progn
      (setq OA_osm (getvar "OSMODE"))
      (setvar "OSMODE" 0)
      (setq qmtk  (car (entsel  "\n选取要删除的签名图块样品："))) 
      (setq vn0 (vlax-ename->vla-object qmtk))
      (setq TKBLK_name (vla-get-name vn0))
      (setq qmdel (ssadd))
      (princ "\n选取要删除签名框的范围...")
      (while (/= (setq ss (ssget  '((0 . "INSERT")))) nil)
             (setq i 0)
             (setq ss_len (sslength ss))
             (while (< i ss_len)
                   (setq en0 (ssname ss i))
                   (setq vn0 (vlax-ename->vla-object en0))
                   (setq BLK_name (vla-get-name vn0))
                   (if (= TKBLK_name BLK_name) (setq qmdel (ssadd en0 qmdel)))
                   (setq i (+ 1 i))
             )
             (command "erase" qmdel "")
             (setq qmdel (ssadd))            
             (princ "\n选取要删除贵人绘图框的范围...")
      )
   )
  )
)


;|*****************************************************************************
OA图框工具：批量修改PDF文件名
|;
;;*****************************************************************************
(defun c:OAPPP()
  (DHK_OADXXPDFGMZ)
)
(defun DHK_OADXXPDFGMZ(/ OA_osm pdfpath filenamelist ss ss_len i i2 MLNUM en0 vn0 
TKBLK_name newname oldname pd pd1 len1 )
    (setq OA_osm (getvar "OSMODE"))
    (setvar "OSMODE" 0)
    (setq pdfpath (vl-filename-directory (getfiled "PDF批量打印文件输出目录" "d:\\" "pdf" 2)))
    (setq filenamelist (vl-directory-files pdfpath "*.pdf" 1))
    (setq i 0)
    (while (/= (setq oldname (nth i filenamelist)) nil)
           (setq len1 (strlen oldname))
           (setq pd (substr oldname (- len1 5) 1))
           (setq pd1 (substr oldname (- len1 6) 1))
           (cond ((= pd "_") 
                    (setq newname (strcat (substr oldname 1 (- len1 5)) "00" (substr oldname (- len1 4))))
                 )
               ((= pd1 "_")
                    (setq newname (strcat (substr oldname 1 (- len1 6)) "0" (substr oldname (- len1 5))))
                )
               (t (setq newname oldname))
            )
            (setq oldname (strcat pdfpath "\\" oldname))
            (setq newname (strcat pdfpath "\\" newname))
            (vl-file-rename oldname newname)
           (setq i (+ 1 i))
    )
    (setq filenamelist (vl-directory-files pdfpath "*.pdf" 1))
    (if  (= Meaad_all_scale nil) (setq meaad_all_scale (getint "\n出图比例因数Meaad_all_scale还没有定义，请输入1：<1,100,200,1000>：")))
    (if  (= Meaad_all_scale nil) (setq meaad_all_scale 1))
    (princ "\n选取要改名的已批量PDF打印的全部图纸（可含目录),应确保原PDF目录下仅为此范围内已批量PDF打印的文件...")
    (setq ss (ssget  '((0 . "INSERT") (2 . "*图框_A*框*"))))
    (setq ss (SORT-SE (SORT-SE ss 10 0 (* 150 Meaad_all_scale) nil) 10 1 (* 150 Meaad_all_scale) T))
    (setq ss_len (sslength ss))
    (setq i 0 i2 0)
    (while (< i ss_len)
                  (setq en0 (ssname ss i))
                  (setq vn0 (vlax-ename->vla-object en0))
                  (setq TKBLK_name (vla-get-name vn0))
                  (if (= TKBLK_name "OA图框_A2_594_横空框")
                       (progn  
                          (setq MLNUM (itoa (+ 1 i2)))
                          (setq newname (strcat pdfpath "\\_目录" MLNUM".pdf"))
                          (setq i2 (+ i2 1))
                       )
                       (progn
                          (setq tzname (OAget_oneatt en0 "图名"))
                          (setq tzname (stripmt tzname))
                          (setq tzname (vl-string-subst "" "\\P" tzname))
                          (setq tznum (OAget_oneatt en0 "图号"))
                          (setq newname (strcat pdfpath "\\" tznum "_" tzname ".pdf"))
                          (setq newname (vl-string-subst "_" "/" newname))
                       )
                   )
                  (setq oldname (strcat pdfpath "\\" (nth i filenamelist)))
                  (vl-file-rename  oldname newname)
                  (setq i (+ 1 i))
    )
    (setvar "OSMODE" OA_osm)
)


;|*****************************************************************************
OA图框工具：批量PC3生成PDF带信息图名
|;
;;*****************************************************************************
(defun DHK_OAPDFPLDY(/ OA_osm pdfpath ss ss_len i i2 MLNUM en0 vn0 
TKBLK_name newname tzname tznum p1 p2 xbl ybl gw pdf_rdexe kjlx en1)
    (setq OA_osm (getvar "OSMODE"))
    (setvar "OSMODE" 0)
    (setq pdfpath (strcat MEAAD_AZML_V31 "plotter\\"))
    (setq pdf_RDEXE (vl-registry-read "HKEY_CLASSES_ROOT\\.pdf"))
    (setq pdf_RDEXE (vl-registry-read (strcat "HKEY_CLASSES_ROOT\\" pdf_RDEXE "\\shell\\Open\\command")))
    (setq pdf_RDEXE  (substr pdf_rdexe 1 (- (strlen pdf_rdexe) 6)))
    (setq n2 (vl-string-position 92 pdf_RDEXE  1 T))
    (setq pdf_rdexe (substr pdf_RDEXE (+ n2 2)))
    (princ "\n选取要批量PDF打印的全部图纸（可含目录)...")
    (setq ss (ssget  '((0 . "INSERT") (2 . "*图框_A*框*"))))
    (setq en1 (ssname ss 0))
    (setq eee (entget en1))
    (setq meaad_all_scale (cdr (assoc 41 eee)))
    (setq ss (SORT-SE (SORT-SE ss 10 0 (* 150 Meaad_all_scale) nil) 10 1 (* 150 Meaad_all_scale) T))
    (setq ss_len (sslength ss))
    (setq kjlx (getvar "tilemode"))
    (setq n2 0)
    (setq i 0 i2 0)
    (while (< i ss_len)
                  (setq en0 (ssname ss i))
                  (setq vn0 (vlax-ename->vla-object en0))
                  (setq TKBLK_name (vla-get-name vn0)) 
                  (setq P1 (oaget_blkpoint en0))               
                  (cond ((wcmatch TKBLK_name "*图框_A3_420_横*") 
                             (setq xbl (*  Meaad_all_Scale 420))
                             (setq ybl (*  Meaad_all_Scale 297))
                             (setq gw "GWA3")
                       )
                      ((wcmatch TKBLK_name "*图框_A3加_472_横*") 
                             (setq xbl (*  Meaad_all_Scale 472))
                             (setq ybl (*  Meaad_all_Scale 297))
                             (setq gw "GWA3_1")
                      )
                      ((wcmatch TKBLK_name "*图框_A3加_525_横*") 
                             (setq xbl (*  Meaad_all_Scale 525))
                             (setq ybl (*  Meaad_all_Scale 297))
                             (setq gw "GWA3_2")
                      )
                      ((wcmatch TKBLK_name "*图框_A3加_630_横*") 
                             (setq xbl (*  Meaad_all_Scale 630))
                             (setq ybl (*  Meaad_all_Scale 297))
                             (setq gw "GWA3_4")
                      )
                      ((wcmatch TKBLK_name "*图框_A3加_735_横*") 
                             (setq xbl (*  Meaad_all_Scale 735))
                             (setq ybl (*  Meaad_all_Scale 297))
                             (setq gw "GWA3_6")
                      )
                      ((wcmatch TKBLK_name "*图框_A3加_840_横*") 
                             (setq xbl (*  Meaad_all_Scale 840))
                             (setq ybl (*  Meaad_all_Scale 297))
                             (setq gw "GWA3_8")
                      )
                      ((wcmatch TKBLK_name "*图框_A2_594_横*") 
                             (setq xbl (*  Meaad_all_Scale 594))
                             (setq ybl (*  Meaad_all_Scale 420))
                             (setq gw "GWA2")
                      )
                      ((wcmatch TKBLK_name "*图框_A2加_668_横*") 
                             (setq xbl (*  Meaad_all_Scale 668))
                             (setq ybl (*  Meaad_all_Scale 420))
                             (setq gw "GWA2_1")
                      )
                      ((wcmatch TKBLK_name "*图框_A2加_742_横*") 
                             (setq xbl (*  Meaad_all_Scale 742))
                             (setq ybl (*  Meaad_all_Scale 420))
                             (setq gw "GWA2_2")
                      )
                      ((wcmatch TKBLK_name "*图框_A2加_891_横*") 
                             (setq xbl (*  Meaad_all_Scale 891))
                             (setq ybl (*  Meaad_all_Scale 420))
                             (setq gw "GWA2_4")
                      )
                      ((wcmatch TKBLK_name "*图框_A2加_1039_横*") 
                             (setq xbl (*  Meaad_all_Scale 1039))
                             (setq ybl (*  Meaad_all_Scale 420))
                             (setq gw "GWA2_6")
                      )
                      ((wcmatch TKBLK_name "*图框_A2加_1188_横*") 
                             (setq xbl (*  Meaad_all_Scale 1188))
                             (setq ybl (*  Meaad_all_Scale 420))
                             (setq gw "GWA2_8")
                      )
                      ((wcmatch TKBLK_name "*图框_A1_841_横*") 
                             (setq xbl (*  Meaad_all_Scale 841))
                             (setq ybl (*  Meaad_all_Scale 594))
                             (setq gw "GWA1")
                      )
                      ((wcmatch TKBLK_name "*图框_A1加_946_横*") 
                             (setq xbl (*  Meaad_all_Scale 946))
                             (setq ybl (*  Meaad_all_Scale 594))
                             (setq gw "GWA1_1")
                      )
                      ((wcmatch TKBLK_name "*图框_A1加_1051_横*") 
                             (setq xbl (*  Meaad_all_Scale 1051))
                             (setq ybl (*  Meaad_all_Scale 594))
                             (setq gw "GWA1_2")
                      )
                      ((wcmatch TKBLK_name "*图框_A1加_1261_横*") 
                             (setq xbl (*  Meaad_all_Scale 1261))
                             (setq ybl (*  Meaad_all_Scale 594))
                             (setq gw "GWA1_4")
                      )
                      ((wcmatch TKBLK_name "*图框_A1加_1471_横*") 
                             (setq xbl (*  Meaad_all_Scale 1471))
                             (setq ybl (*  Meaad_all_Scale 594))
                             (setq gw "GWA1_6")
                      )
                      ((wcmatch TKBLK_name "*图框_A1加_1682_横*") 
                             (setq xbl (*  Meaad_all_Scale 1682))
                             (setq ybl (*  Meaad_all_Scale 594))
                             (setq gw "GWA1_8")
                      )
                      ((wcmatch TKBLK_name "*图框_A0_1189_横*") 
                             (setq xbl (*  Meaad_all_Scale 1189))
                             (setq ybl (*  Meaad_all_Scale 841))
                             (setq gw "GWA0")
                      )
                      ((wcmatch TKBLK_name "*图框_A0加_1337_横*") 
                             (setq xbl (*  Meaad_all_Scale 1337))
                             (setq ybl (*  Meaad_all_Scale 841))
                             (setq gw "GWA0_1")
                      )
                      ((wcmatch TKBLK_name "*图框_A0加_1486_横*") 
                             (setq xbl (*  Meaad_all_Scale 1486))
                             (setq ybl (*  Meaad_all_Scale 841))
                             (setq gw "GWA0_2")
                      )
                      ((wcmatch TKBLK_name "*图框_A0加_1783_横*") 
                             (setq xbl (*  Meaad_all_Scale 1783))
                             (setq ybl (*  Meaad_all_Scale 841))
                             (setq gw "GWA0_4")
                      )
                      ((wcmatch TKBLK_name "*图框_A0加_2080_横*") 
                             (setq xbl (*  Meaad_all_Scale 2080))
                             (setq ybl (*  Meaad_all_Scale 841))
                             (setq gw "GWA0_6")
                      )
                      ((wcmatch TKBLK_name "*图框_A0加_2378_横*") 
                             (setq xbl (*  Meaad_all_Scale 2378))
                             (setq ybl (*  Meaad_all_Scale 841))
                             (setq gw "GWA0_8")
                      )
                   )
                   (setq p2 (polar p1 0 xbl))
                   (setq p2 (polar p2 (dtr 90) ybl))
                   (if (= TKBLK_name "OA图框_A2_594_横空框")
                       (progn  
                          (setq MLNUM (itoa (+ 1 i2)))
                          (setq newname (strcat pdfpath "目录" MLNUM".pdf")) 
                          (setq i2 (+ i2 1))
                       )
                       (progn
                          (setq tzname (OAget_oneatt en0 "图名"))
                          (setq tzname (stripmt tzname))
                          (setq tzname (vl-string-subst "" "\\P" tzname))
                          (setq tznum (OAget_oneatt en0 "图号"))
                          (setq newname (strcat pdfpath tznum "_" tzname))
                          (while (/= nil (vl-string-search "/" newname))
                              (setq newname (vl-string-subst "_" "/" newname))
                          )

                       )
                   )
                  (setq newname (strcat newname  ".pdf"))
                  (if (= kjlx 1)
                   (command "-plot" "Y" "" "meaad.pc3" gw "M" "L" "" "W" p1 p2 "F" "C" "Y" "MEAAD.ctb" "Y" "W" newname "N" "Y")
                   (command "-plot" "Y" "" "meaad.pc3" gw "M" "L" "" "W" p1 p2 "F" "C" "Y" "MEAAD.ctb" "Y" "N" "N"  "N" newname "N" "Y")
                  )
                   (if (= n2 10) (progn (setq n2 0) (command "shell" (strcat "taskkill /IM \"" pdf_rdexe "\" /F"))))                           
                   (setq i (+ 1 i))
                   (setq n2 (+ 1 n2))
    )
    (setvar "OSMODE" OA_osm)
    (command "shell" (strcat "taskkill /IM \"" pdf_rdexe "\" /F"))
)




;|*****************************************************************************
OA图框工具：工程量估算
|;
;;*****************************************************************************
(defun DHK_OATZSLTJ(/ OA_osm ss i ss_len tzA2_SUM tza2_CKSUM gcs gcs_num en0 tznum ecth tztf 
new_sjr new_xhr tzkd b0 b1 b2 b3 TJJG n sjr_num xhr_num gcs0)
    (setq OA_osm (getvar "OSMODE"))
    (setvar "OSMODE" 0)
    (princ "\n选取全部目录...")
    (setq SS (ssget '((0 . "INSERT") (2 . "OA图框_图纸目录单行"))))
    (setq i 0)
    (setq ss_len (sslength ss))
    (setq tzA2_SUM 0); 总张数
    (setq tza2_CKSUM 0) ;参考图总量
    (setq gcs "") ;工程师
    (setq gcs_num 0);工程师数量
    (while (< i ss_len)
          (setq en0 (ssname ss i))
          (setq tznum (oaget_oneatt en0 "张数"))
          (setq ecth (oaget_oneatt en0 "二次图号")) 
          (setq tztf (oaget_oneatt en0 "图幅"))
          (setq new_sjr (oaget_oneatt en0 "图纸设计人"))
          (setq new_xhr (oaget_oneatt en0 "图纸校核人"))
          (setq tzkd (atoi (substr tztf 4)))
          (cond ((wcmatch tztf "*A0*") 
                     (setq tzA2_SUM (+ tzA2_SUM (* (atoi tznum) 4.0 (/ tzkd 1189.0)))) 
                     (if (/= ecth "") (setq tzA2_ckSUM (+ tzA2_ckSUM (* (atoi tznum) 4.0 (/ tzkd 1189.0))))) 
                 )
                ((wcmatch tztf "*A1*") (setq tzA2_SUM (+ tzA2_SUM (* (atoi tznum) 2.0 (/ tzkd 841.0))))
                     (if (/= ecth "") (setq tzA2_ckSUM (+ tzA2_ckSUM (* (atoi tznum) 2.0 (/ tzkd 841.0))))) 
                 )
                ((wcmatch tztf "*A2*") (setq tzA2_SUM (+ tzA2_SUM (* (atoi tznum) 1.0 (/ tzkd 594.0))))
                     (if (/= ecth "") (setq tzA2_ckSUM (+ tzA2_ckSUM (* (atoi tznum) 1.0 (/ tzkd 594.0))))) 
                 )
                ((wcmatch tztf "*A3*") (setq tzA2_SUM (+ tzA2_SUM (* (atoi tznum) 0.5 (/ tzkd 420.0))))
                     (if (/= ecth "") (setq tzA2_ckSUM (+ tzA2_ckSUM (* (atoi tznum) 0.5 (/ tzkd 420.0))))) 
                 )
          )
          (if (= i 0) (setq gcs (strcat new_sjr ";"  new_xhr) gcs_num 2)
                      (progn
                         (if (= nil (vl-string-search new_sjr gcs)) (setq gcs (strcat gcs ";" new_sjr)  gcs_num (1+ gcs_num)))
                         (if (= nil (vl-string-search new_xhr gcs)) (setq gcs (strcat gcs ";" new_xhr)  gcs_num (1+ gcs_num)))
                      )
          )
         (setq i (+ 1 i))
    )
    (setq b0 "--------- 工程设计工程量估算（按A2算) ---------")
    (setq b1 (strcat "\n图纸设计总量:   A2*" (rtos tzA2_SUM 2 1)))
    (setq b2 (strcat "\n其中参考图纸总量:   A2*" (rtos tzA2_ckSUM 2 1)))
    (setq b3 "\n\n------------个人工作量（不含参考图）-------------") 
    (setq TJJG (strcat b0 b1 b2 b3))
    (setq n 0)
    (setq gcs (parse7 gcs ";"))
    (repeat gcs_num
          (setq gcs0 (nth n gcs))
          (setq sjr_num 0)
          (setq xhr_num 0)
          (setq i 0)
          (while (< i ss_len)
             (setq en0 (ssname ss i))
             (setq tznum (oaget_oneatt en0 "张数"))
             (setq ecth (oaget_oneatt en0 "二次图号")) 
             (setq tztf (oaget_oneatt en0 "图幅"))
             (setq new_sjr (oaget_oneatt en0 "图纸设计人"))
             (setq new_xhr (oaget_oneatt en0 "图纸校核人"))
             (setq tzkd (atoi (substr tztf 4)))
             (if (and (= gcs0 new_sjr) (= ecth ""))
                 (progn
                    (cond ((wcmatch tztf "*A0*") (setq sjr_num (+ sjr_num (* (atoi tznum) 4.0 (/ tzkd 1189.0)))))
                          ((wcmatch tztf "*A1*") (setq sjr_num (+ sjr_num (* (atoi tznum) 2.0 (/ tzkd 841.0)))))
                          ((wcmatch tztf "*A2*") (setq sjr_num (+ sjr_num (* (atoi tznum) 1.0 (/ tzkd 594.0)))))
                          ((wcmatch tztf "*A3*") (setq sjr_num (+ sjr_num (* (atoi tznum) 0.5 (/ tzkd 420.0)))))
                     )
             ))
             (if (and (= gcs0 new_xhr) (= ecth ""))
                 (progn
                    (cond ((wcmatch tztf "*A0*") (setq xhr_num (+ xhr_num (* (atoi tznum) 4.0 (/ tzkd 1189.0)))))
                          ((wcmatch tztf "*A1*") (setq xhr_num (+ xhr_num (* (atoi tznum) 2.0 (/ tzkd 841.0)))))
                          ((wcmatch tztf "*A2*") (setq xhr_num (+ xhr_num (* (atoi tznum) 1.0 (/ tzkd 594.0)))))
                          ((wcmatch tztf "*A3*") (setq xhr_num (+ xhr_num (* (atoi tznum) 0.5 (/ tzkd 420.0)))))
                     )
             ))
             (setq i (+ i 1))
         )
         (setq TJJG (strcat TJJG "\n" gcs0 "   设计量: A2*" (rtos sjr_num 2 1) ";   校核量: A2*" (rtos xhr_num 2 1)))
         (setq n (+ n 1))
      )
    (alert TJJG)
)



;***************************************************************************
;;;传统工具集
;;;多页底框附件
;;;***************************************************************************
(defun DHK_OADYCKFJ(/ st ist DQ2y_osm nst nist en0 vn0 ecth)
  (if  (= Meaad_all_scale nil) (setq meaad_all_scale (getint "\n出图比例因数Meaad_all_scale还没有定义，请输入1：<1,100,200,1000>：")))
    (if  (= Meaad_all_scale nil) (setq meaad_all_scale 1))
  (setq DQ2y_osm (getvar "OSMODE"))
  (setvar "OSMODE" 0)
  (while (/= nil (setq en0  (car (entsel  "\n选取二次图号：")))) 
     (setq vn0 (vlax-ename->vla-object en0))
     (setq ecth (vla-get-TextString vn0))
     (setq st (getint "\n总张数<2>?"))
     (if (= st nil) (setq st 2))
     (command "osnap" "int")
     (setq ist 1)
     (if (> st 9) (setq nst (itoa st)) (setq nst (strcat "0" (itoa st))))
     (repeat st
        (if (> ist 9) (setq nist (itoa ist)) (setq nist (strcat "0" (itoa ist))))
        (command "insert" "OA图框_二次图标签" pause meaad_all_scale meaad_all_scale "")
        (oaput_oneatt (entlast) "张数" nst)
        (oaput_oneatt (entlast) "序号" nist)
        (oaput_oneatt (entlast) "二次图号" ecth)    
        (setq ist (+ 1 ist))
     )
   )
  (setvar "OSMODE" DQ2y_osm)
)


;***************************************************************************
;;;传统工具集
;;;非OA图框图名图号传递
;;;***************************************************************************
(defun DHK_OATMTHCD(/ DQ2y_osm  en0 en1 en2 vn1 vn2 TZname TZnum)
  (setq DQ2y_osm (getvar "OSMODE"))
  (setvar "OSMODE" 0)
  (while (/= nil (setq en0  (car (entsel  "\n选取目标OA图框："))))
      (setq en1  (car (entsel  "\n选取对应图名："))) 
      (setq vn1 (vlax-ename->vla-object en1))
      (setq en2  (car (entsel  "\n选取对应图号："))) 
      (setq vn2 (vlax-ename->vla-object en2))
      (setq TZname (vla-get-TextString vn1))
      (setq TZnum  (vla-get-TextString vn2))
      (oaput_oneatt en0 "图名" TZname)
      (oaput_oneatt en0 "图号" TZnum)
  )
  (setvar "OSMODE" DQ2y_osm)
)

;***************************************************************************
;;;传统工具集
;;;杨睿高压图属性标签转txt根据
;;;***************************************************************************
(defun c:yrtxt(/ ss ss_len en vn ro h p nr n)
    (princ "\n选取全部属性定义...")
    (setq SS (ssget '((0 . "ATTDEF") (100 . "AcDbAttributeDefinition"))))
    (setq ss_len (sslength ss))
    (setq n 0)
    (while (< n ss_len)
         (setq en (ssname ss n))
         (setq vn (vlax-ename->vla-object en))
         (setq h (vla-get-height vn))
         (setq ro (vla-get-Rotation vn))
         (setq nr (vla-get-TagString vn))
         (setq p (vla-get-InsertionPoint vn))
         (setq p (vlax-variant-value p))
         (setq p (vlax-safearray->list p))
         (command "erase" en "")
         (command "text" "s" "sj2ydq_文本" p h ro nr)
         (setq n (+ n 1))
   )
)
